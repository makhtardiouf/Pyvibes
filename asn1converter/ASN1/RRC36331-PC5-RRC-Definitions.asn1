-- 
-- ASN.1 module found by ./crfc2asn1.pl in EUTRA-RRC36331.txt at line 18310
-- 

PC5-RRC-Definitions DEFINITIONS AUTOMATIC TAGS ::=

BEGIN

IMPORTS
	TDD-ConfigSL-r12
FROM EUTRA-RRC-Definitions;

-- ASN1STOP

-	SBCCH-SL-BCH-Message
The SBCCH-SL-BCH-Message class is the set of RRC messages that may be sent from the UE to the UE via SL-BCH on the SBCCH logical channel.
-- ASN1START

SBCCH-SL-BCH-Message ::= SEQUENCE {
	message					SBCCH-SL-BCH-MessageType
}

SBCCH-SL-BCH-MessageType ::=						MasterInformationBlock-SL

-- ASN1STOP

6.5.2	Message definitions
-	MasterInformationBlock-SL
The MasterInformationBlock-SL includes the information transmitted by a UE transmitting SLSS, i.e. acting as synchronisation reference, via SL-BCH.
Signalling radio bearer: N/A
RLC-SAP: TM
Logical channel: SBCCH
Direction: UE to UE
MasterInformationBlock-SL
-- ASN1START

MasterInformationBlock-SL ::=		SEQUENCE {
	sl-Bandwidth-r12					ENUMERATED {
											n6, n15, n25, n50, n75, n100},
	tdd-ConfigSL-r12					TDD-ConfigSL-r12,
	directFrameNumber-r12				BIT STRING (SIZE (10)),
	directSubframeNumber-r12			INTEGER (0..9),
	inCoverage-r12						BOOLEAN,
	reserved-r12						BIT STRING (SIZE (19))
}


-- ASN1STOP

MasterInformationBlock-SL field descriptions
directFrameNumber
Indicates the frame number in which SLSS and SL-BCH are transmitted. The subframe in the frame corresponding to directFrameNumber is indicated by directSubframeNumber.
inCoverage
Value TRUE indicates that the UE transmitting the MasterInformationBlock-SL is in E-UTRAN coverage.
sl-Bandwidth
Parameter: transmission bandwidth configuration. n6 corresponds to 6 resource blocks, n15 to 15 resource blocks and so on.

-	End of PC5-RRC-Definitions
-- ASN1START

END
