-- 
-- ASN.1 module found by ./crfc2asn1.pl in EUTRA-RRC36331.txt at line 4853
-- 

EUTRA-RRC-Definitions DEFINITIONS AUTOMATIC TAGS ::=

BEGIN

-- ASN1STOP

-	BCCH-BCH-Message
The BCCH-BCH-Message class is the set of RRC messages that may be sent from the E-UTRAN to the UE via BCH on the BCCH logical channel.
-- ASN1START

BCCH-BCH-Message ::= SEQUENCE {
	message					BCCH-BCH-MessageType
}

BCCH-BCH-MessageType ::=						MasterInformationBlock

-- ASN1STOP

-	BCCH-DL-SCH-Message
The BCCH-DL-SCH-Message class is the set of RRC messages that may be sent from the E-UTRAN to the UE via DL-SCH on the BCCH logical channel.
-- ASN1START

BCCH-DL-SCH-Message ::= SEQUENCE {
	message					BCCH-DL-SCH-MessageType
}

BCCH-DL-SCH-MessageType ::= CHOICE {
	c1						CHOICE {
		systemInformation						SystemInformation,
		systemInformationBlockType1				SystemInformationBlockType1
	},
	messageClassExtension	SEQUENCE {}
}

-- ASN1STOP

-	MCCH-Message
The MCCH-Message class is the set of RRC messages that may be sent from the E-UTRAN to the UE on the MCCH logical channel.
-- ASN1START

MCCH-Message ::= 		SEQUENCE {
	message					MCCH-MessageType
}

MCCH-MessageType ::= CHOICE {
	c1							CHOICE {
		mbsfnAreaConfiguration-r9		MBSFNAreaConfiguration-r9
	},
	later						CHOICE {
		c2								CHOICE{
			mbmsCountingRequest-r10			MBMSCountingRequest-r10
		},
		messageClassExtension	SEQUENCE {}
	}
}

-- ASN1STOP

-	PCCH-Message
The PCCH-Message class is the set of RRC messages that may be sent from the E-UTRAN to the UE on the PCCH logical channel.
-- ASN1START

PCCH-Message ::= SEQUENCE {
	message					PCCH-MessageType
}

PCCH-MessageType ::= CHOICE {
	c1						CHOICE {
		paging									Paging
	},
	messageClassExtension	SEQUENCE {}
}

-- ASN1STOP

-	DL-CCCH-Message
The DL-CCCH-Message class is the set of RRC messages that may be sent from the E-UTRAN to the UE on the downlink CCCH logical channel.
-- ASN1START

DL-CCCH-Message ::= SEQUENCE {
	message					DL-CCCH-MessageType
}

DL-CCCH-MessageType ::= CHOICE {
	c1						CHOICE {
		rrcConnectionReestablishment			RRCConnectionReestablishment,
		rrcConnectionReestablishmentReject		RRCConnectionReestablishmentReject,
		rrcConnectionReject						RRCConnectionReject,
		rrcConnectionSetup						RRCConnectionSetup
	},
	messageClassExtension	SEQUENCE {}
}

-- ASN1STOP

-	DL-DCCH-Message
The DL-DCCH-Message class is the set of RRC messages that may be sent from the E-UTRAN to the UE or from the E-UTRAN to the RN on the downlink DCCH logical channel.
-- ASN1START

DL-DCCH-Message ::= SEQUENCE {
	message					DL-DCCH-MessageType
}

DL-DCCH-MessageType ::= CHOICE {
	c1						CHOICE {
		csfbParametersResponseCDMA2000			CSFBParametersResponseCDMA2000,
		dlInformationTransfer					DLInformationTransfer,
		handoverFromEUTRAPreparationRequest		HandoverFromEUTRAPreparationRequest,
		mobilityFromEUTRACommand				MobilityFromEUTRACommand,
		rrcConnectionReconfiguration			RRCConnectionReconfiguration,
		rrcConnectionRelease					RRCConnectionRelease,
		securityModeCommand						SecurityModeCommand,
		ueCapabilityEnquiry						UECapabilityEnquiry,
		counterCheck							CounterCheck,
		ueInformationRequest-r9					UEInformationRequest-r9,
		loggedMeasurementConfiguration-r10		LoggedMeasurementConfiguration-r10,
		rnReconfiguration-r10					RNReconfiguration-r10,
		spare4 NULL,
		spare3 NULL, spare2 NULL, spare1 NULL
	},
	messageClassExtension	SEQUENCE {}
}

-- ASN1STOP

-	UL-CCCH-Message
The UL-CCCH-Message class is the set of RRC messages that may be sent from the UE to the E-UTRAN on the uplink CCCH logical channel.
-- ASN1START

UL-CCCH-Message ::= SEQUENCE {
	message					UL-CCCH-MessageType
}

UL-CCCH-MessageType ::= CHOICE {
	c1						CHOICE {
		rrcConnectionReestablishmentRequest		RRCConnectionReestablishmentRequest,
		rrcConnectionRequest					RRCConnectionRequest
	},
	messageClassExtension	SEQUENCE {}
}

-- ASN1STOP

-	UL-DCCH-Message
The UL-DCCH-Message class is the set of RRC messages that may be sent from the UE to the E-UTRAN or from the RN to the E-UTRAN on the uplink DCCH logical channel.
-- ASN1START

UL-DCCH-Message ::= SEQUENCE {
	message					UL-DCCH-MessageType
}

UL-DCCH-MessageType ::= CHOICE {
	c1						CHOICE {
		csfbParametersRequestCDMA2000			CSFBParametersRequestCDMA2000,
		measurementReport						MeasurementReport,
		rrcConnectionReconfigurationComplete	RRCConnectionReconfigurationComplete,
		rrcConnectionReestablishmentComplete	RRCConnectionReestablishmentComplete,
		rrcConnectionSetupComplete				RRCConnectionSetupComplete,
		securityModeComplete					SecurityModeComplete,
		securityModeFailure						SecurityModeFailure,
		ueCapabilityInformation					UECapabilityInformation,
		ulHandoverPreparationTransfer			ULHandoverPreparationTransfer,
		ulInformationTransfer					ULInformationTransfer,
		counterCheckResponse					CounterCheckResponse,
		ueInformationResponse-r9				UEInformationResponse-r9,
		proximityIndication-r9					ProximityIndication-r9,
		rnReconfigurationComplete-r10			RNReconfigurationComplete-r10,
		mbmsCountingResponse-r10				MBMSCountingResponse-r10,
		interFreqRSTDMeasurementIndication-r10	InterFreqRSTDMeasurementIndication-r10
	},
	messageClassExtension	CHOICE {
		c2							CHOICE {
			ueAssistanceInformation-r11			UEAssistanceInformation-r11,
			inDeviceCoexIndication-r11			InDeviceCoexIndication-r11,
			mbmsInterestIndication-r11			MBMSInterestIndication-r11,
			scgFailureInformation-r12			SCGFailureInformation-r12,
			sidelinkUEInformation-r12			SidelinkUEInformation-r12,
			spare11 NULL, spare10 NULL,
			spare9 NULL, spare8 NULL, spare7 NULL,
			spare6 NULL, spare5 NULL, spare4 NULL,
			spare3 NULL, spare2 NULL, spare1 NULL
		},
		messageClassExtensionFuture-r11	SEQUENCE {}
	}
}

-- ASN1STOP

-	SC-MCCH-Message
The SC-MCCH-Message class is the set of RRC messages that may be sent from the E-UTRAN to the UE on the SC-MCCH logical channel.
-- ASN1START

SC-MCCH-Message ::= SEQUENCE {
	message					SC-MCCH-MessageType
}


SC-MCCH-MessageType ::= CHOICE {
	c1						CHOICE {
		scptmConfiguration-r13						SCPTMConfiguration-r13
	},
	messageClassExtension	SEQUENCE {}
}

-- ASN1STOP

6.2.2	Message definitions
-	CounterCheck
The CounterCheck message is used by the E-UTRAN to indicate the current COUNT MSB values associated to each DRB and to request the UE to compare these to its COUNT MSB values and to report the comparison results to E-UTRAN.
Signalling radio bearer: SRB1
RLC-SAP: AM
Logical channel: DCCH
Direction: E-UTRAN to UE
CounterCheck message
-- ASN1START

CounterCheck ::=			SEQUENCE {
	rrc-TransactionIdentifier			RRC-TransactionIdentifier,
	criticalExtensions					CHOICE {
		c1									CHOICE {
			counterCheck-r8						CounterCheck-r8-IEs,
			spare3 NULL, spare2 NULL, spare1 NULL
		},
		criticalExtensionsFuture			SEQUENCE {}
	}
}

CounterCheck-r8-IEs ::=	SEQUENCE {
	drb-CountMSB-InfoList				DRB-CountMSB-InfoList,
	nonCriticalExtension				CounterCheck-v8a0-IEs				OPTIONAL
}

CounterCheck-v8a0-IEs ::= SEQUENCE {
	lateNonCriticalExtension			OCTET STRING						OPTIONAL,
	nonCriticalExtension				SEQUENCE {}							OPTIONAL
}

DRB-CountMSB-InfoList ::=		SEQUENCE (SIZE (1..maxDRB)) OF DRB-CountMSB-Info

DRB-CountMSB-Info ::=	SEQUENCE {
	drb-Identity					DRB-Identity,
	countMSB-Uplink					INTEGER(0..33554431),
	countMSB-Downlink				INTEGER(0..33554431)
}

-- ASN1STOP

CounterCheck field descriptions
count-MSB-Downlink
Indicates the value of 25 MSBs from downlink COUNT associated to this DRB.
count-MSB-Uplink
Indicates the value of 25 MSBs from uplink COUNT associated to this DRB.
drb-CountMSB-InfoList
Indicates the MSBs of the COUNT values of the DRBs.

-	CounterCheckResponse
The CounterCheckResponse message is used by the UE to respond to a CounterCheck message.
Signalling radio bearer: SRB1
RLC-SAP: AM
Logical channel: DCCH
Direction: UE to E-UTRAN
CounterCheckResponse message
-- ASN1START

CounterCheckResponse ::=			SEQUENCE {
	rrc-TransactionIdentifier			RRC-TransactionIdentifier,
	criticalExtensions					CHOICE {
		counterCheckResponse-r8				CounterCheckResponse-r8-IEs,
		criticalExtensionsFuture			SEQUENCE {}
	}
}

CounterCheckResponse-r8-IEs ::=	SEQUENCE {
	drb-CountInfoList					DRB-CountInfoList,
	nonCriticalExtension				CounterCheckResponse-v8a0-IEs		OPTIONAL
}

CounterCheckResponse-v8a0-IEs ::= SEQUENCE {
	lateNonCriticalExtension			OCTET STRING						OPTIONAL,
	nonCriticalExtension				SEQUENCE {}							OPTIONAL
}

DRB-CountInfoList ::=			SEQUENCE (SIZE (0..maxDRB)) OF DRB-CountInfo

DRB-CountInfo ::=	SEQUENCE {
	drb-Identity					DRB-Identity,
	count-Uplink					INTEGER(0..4294967295),
	count-Downlink					INTEGER(0..4294967295)
}

-- ASN1STOP

CounterCheckResponse field descriptions
count-Downlink
Indicates the value of downlink COUNT associated to this DRB.
count-Uplink
Indicates the value of uplink COUNT associated to this DRB.
drb-CountInfoList
Indicates the COUNT values of the DRBs.

-	CSFBParametersRequestCDMA2000
The CSFBParametersRequestCDMA2000 message is used by the UE to obtain the CDMA2000 1xRTT Parameters from the network. The UE needs these parameters to generate the CDMA2000 1xRTT Registration message used to register with the CDMA2000 1xRTT Network which is required to support CSFB to CDMA2000 1xRTT.
Signalling radio bearer: SRB1
RLC-SAP: AM
Logical channel: DCCH
Direction: UE to E-UTRAN
CSFBParametersRequestCDMA2000 message
-- ASN1START

CSFBParametersRequestCDMA2000 ::= SEQUENCE {
	criticalExtensions					CHOICE {
		csfbParametersRequestCDMA2000-r8	CSFBParametersRequestCDMA2000-r8-IEs,
		criticalExtensionsFuture			SEQUENCE {}
	}
}

CSFBParametersRequestCDMA2000-r8-IEs ::= SEQUENCE {
	nonCriticalExtension				CSFBParametersRequestCDMA2000-v8a0-IEs	OPTIONAL
}

CSFBParametersRequestCDMA2000-v8a0-IEs ::= SEQUENCE {
	lateNonCriticalExtension			OCTET STRING						OPTIONAL,
	nonCriticalExtension				SEQUENCE {}							OPTIONAL
}

-- ASN1STOP

-	CSFBParametersResponseCDMA2000
The CSFBParametersResponseCDMA2000 message is used to provide the CDMA2000 1xRTT Parameters to the UE so the UE can register with the CDMA2000 1xRTT Network to support CSFB to CDMA2000 1xRTT.
Signalling radio bearer: SRB1
RLC-SAP: AM
Logical channel: DCCH
Direction: E-UTRAN to UE
CSFBParametersResponseCDMA2000 message
-- ASN1START

CSFBParametersResponseCDMA2000 ::= SEQUENCE {
	rrc-TransactionIdentifier			RRC-TransactionIdentifier,
	criticalExtensions						CHOICE {
		csfbParametersResponseCDMA2000-r8		CSFBParametersResponseCDMA2000-r8-IEs,
		criticalExtensionsFuture				SEQUENCE {}
	}
}

CSFBParametersResponseCDMA2000-r8-IEs ::= SEQUENCE {
	rand								RAND-CDMA2000,
	mobilityParameters					MobilityParametersCDMA2000,
	nonCriticalExtension				CSFBParametersResponseCDMA2000-v8a0-IEs	OPTIONAL
}

CSFBParametersResponseCDMA2000-v8a0-IEs ::= SEQUENCE {
	lateNonCriticalExtension			OCTET STRING						OPTIONAL,
	nonCriticalExtension				SEQUENCE {}							OPTIONAL
}

-- ASN1STOP

-	DLInformationTransfer
The DLInformationTransfer message is used for the downlink transfer of NAS or non-3GPP dedicated information.
Signalling radio bearer: SRB2 or SRB1 (only if SRB2 not established yet. If SRB2 is suspended, E-UTRAN does not send this message until SRB2 is resumed.)
RLC-SAP: AM
Logical channel: DCCH
Direction: E-UTRAN to UE
DLInformationTransfer message
-- ASN1START

DLInformationTransfer ::=			SEQUENCE {
	rrc-TransactionIdentifier			RRC-TransactionIdentifier,
	criticalExtensions					CHOICE {
		c1									CHOICE {
			dlInformationTransfer-r8			DLInformationTransfer-r8-IEs,
			spare3 NULL, spare2 NULL, spare1 NULL
		},
		criticalExtensionsFuture			SEQUENCE {}
	}
}

DLInformationTransfer-r8-IEs ::=	SEQUENCE {
	dedicatedInfoType					CHOICE {
		dedicatedInfoNAS					DedicatedInfoNAS,
		dedicatedInfoCDMA2000-1XRTT			DedicatedInfoCDMA2000,
		dedicatedInfoCDMA2000-HRPD			DedicatedInfoCDMA2000
	},
	nonCriticalExtension				DLInformationTransfer-v8a0-IEs		OPTIONAL
}

DLInformationTransfer-v8a0-IEs ::= SEQUENCE {
	lateNonCriticalExtension			OCTET STRING						OPTIONAL,
	nonCriticalExtension				SEQUENCE {}							OPTIONAL
}

-- ASN1STOP

-	HandoverFromEUTRAPreparationRequest (CDMA2000)
The HandoverFromEUTRAPreparationRequest message is used to trigger the handover preparation procedure with a CDMA2000 RAT. This message is also used to trigger a tunneled preparation procedure with a CDMA2000 1xRTT RAT to obtain traffic channel resources for the enhanced CS fallback to CDMA2000 1xRTT, which may also involve a concurrent preparation for handover to CDMA2000 HRPD. Also, this message is used to trigger the dual Rx/Tx redirection procedure with a CDMA2000 1xRTT RAT.
Signalling radio bearer: SRB1
RLC-SAP: AM
Logical channel: DCCH
Direction: E-UTRAN to UE
HandoverFromEUTRAPreparationRequest message
-- ASN1START

HandoverFromEUTRAPreparationRequest ::= SEQUENCE {
	rrc-TransactionIdentifier		RRC-TransactionIdentifier,
	criticalExtensions					CHOICE {
		c1									CHOICE {
			handoverFromEUTRAPreparationRequest-r8
												HandoverFromEUTRAPreparationRequest-r8-IEs,
			spare3 NULL, spare2 NULL, spare1 NULL
		},
		criticalExtensionsFuture			SEQUENCE {}
	}
}

HandoverFromEUTRAPreparationRequest-r8-IEs ::= SEQUENCE {
	cdma2000-Type					CDMA2000-Type,
	rand							RAND-CDMA2000				OPTIONAL,	-- Cond cdma2000-Type
	mobilityParameters				MobilityParametersCDMA2000	OPTIONAL,	-- Cond cdma2000-Type
	nonCriticalExtension			HandoverFromEUTRAPreparationRequest-v890-IEs	OPTIONAL
}

HandoverFromEUTRAPreparationRequest-v890-IEs ::= SEQUENCE {
	lateNonCriticalExtension		OCTET STRING				OPTIONAL,
	nonCriticalExtension			HandoverFromEUTRAPreparationRequest-v920-IEs	OPTIONAL
}

HandoverFromEUTRAPreparationRequest-v920-IEs ::= SEQUENCE {
	concurrPrepCDMA2000-HRPD-r9		BOOLEAN					OPTIONAL,	-- Cond cdma2000-Type
	nonCriticalExtension			HandoverFromEUTRAPreparationRequest-v1020-IEs	OPTIONAL
}

HandoverFromEUTRAPreparationRequest-v1020-IEs ::= SEQUENCE {
	dualRxTxRedirectIndicator-r10		ENUMERATED {true}		OPTIONAL,	-- Cond cdma2000-1XRTT
	redirectCarrierCDMA2000-1XRTT-r10	CarrierFreqCDMA2000		OPTIONAL,	-- Cond dualRxTxRedirect
	nonCriticalExtension				SEQUENCE {}				OPTIONAL
}

-- ASN1STOP

HandoverFromEUTRAPreparationRequest field descriptions
concurrPrepCDMA2000-HRPD
Value TRUE indicates that upper layers should initiate concurrent preparation for handover to CDMA2000 HRPD in addition to preparation for enhanced CS fallback to CDMA2000 1xRTT.
dualRxTxRedirectIndicator
Value TRUE indicates that the second radio of the dual Rx/Tx UE is being redirected to CDMA2000 1xRTT [51].
redirectCarrierCDMA2000-1XRTT
Used to indicate the CDMA2000 1xRTT carrier frequency where the UE is being redirected to.

Conditional presence
Explanation
cdma2000-1XRTT
The field is optionally present, need ON, if the cdma2000-Type = type1XRTT; otherwise it is not present.
cdma2000-Type
The field is mandatory present if the cdma2000-Type = type1XRTT; otherwise it is not present.
dualRxTxRedirect
The field is optionally present, need ON, if dualRxTxRedirectIndicator is present; otherwise it is not present.

-	InDeviceCoexIndication
The InDeviceCoexIndication message is used to inform E-UTRAN about IDC problems which can not be solved by the UE itself, as well as to provide information that may assist E-UTRAN when resolving these problems.
Signalling radio bearer: SRB1
RLC-SAP: AM
Logical channel: DCCH
Direction: UE to E-UTRAN
InDeviceCoexIndication message
-- ASN1START

InDeviceCoexIndication-r11 ::=		SEQUENCE {
	criticalExtensions					CHOICE {
		c1									CHOICE {
			inDeviceCoexIndication-r11				InDeviceCoexIndication-r11-IEs,
			spare3 NULL, spare2 NULL, spare1 NULL
		},
		criticalExtensionsFuture			SEQUENCE {}
	}
}

InDeviceCoexIndication-r11-IEs ::=	SEQUENCE {
	affectedCarrierFreqList-r11			AffectedCarrierFreqList-r11					OPTIONAL,
	tdm-AssistanceInfo-r11				TDM-AssistanceInfo-r11						OPTIONAL,
	lateNonCriticalExtension			OCTET STRING								OPTIONAL,
	nonCriticalExtension				InDeviceCoexIndication-v11d0-IEs			OPTIONAL
}

InDeviceCoexIndication-v11d0-IEs ::=	SEQUENCE {
	ul-CA-AssistanceInfo-r11			SEQUENCE {
		affectedCarrierFreqCombList-r11	AffectedCarrierFreqCombList-r11			OPTIONAL, 
		victimSystemType-r11				VictimSystemType-r11
	}																			OPTIONAL,
	nonCriticalExtension				SEQUENCE {}								OPTIONAL
}

AffectedCarrierFreqList-r11 ::=	SEQUENCE (SIZE (1..maxFreqIDC-r11)) OF AffectedCarrierFreq-r11

AffectedCarrierFreq-r11 ::=	SEQUENCE {
	carrierFreq-r11				MeasObjectId,
	interferenceDirection-r11	ENUMERATED {eutra, other, both, spare}
}

AffectedCarrierFreqCombList-r11 ::=	SEQUENCE (SIZE (1..maxCombIDC-r11)) OF AffectedCarrierFreqComb-r11

AffectedCarrierFreqComb-r11 ::=	SEQUENCE (SIZE (2..maxServCell-r10)) OF MeasObjectId

TDM-AssistanceInfo-r11 ::=	CHOICE {
	drx-AssistanceInfo-r11				SEQUENCE {
		drx-CycleLength-r11					ENUMERATED {sf40, sf64, sf80, sf128, sf160,
												 sf256, spare2, spare1},
		drx-Offset-r11						INTEGER (0..255)	OPTIONAL,
		drx-ActiveTime-r11					ENUMERATED {sf20, sf30, sf40, sf60, sf80,
												 sf100, spare2, spare1}
	},
	idc-SubframePatternList-r11			IDC-SubframePatternList-r11,
	...
}

IDC-SubframePatternList-r11 ::=	SEQUENCE (SIZE (1..maxSubframePatternIDC-r11)) OF IDC-SubframePattern-r11

IDC-SubframePattern-r11 ::= CHOICE {
	subframePatternFDD-r11				BIT STRING (SIZE (4)),
	subframePatternTDD-r11				CHOICE {
		subframeConfig0-r11					BIT STRING (SIZE (70)),
		subframeConfig1-5-r11				BIT STRING (SIZE (10)),
		subframeConfig6-r11					BIT STRING (SIZE (60))
	},
	...
}

VictimSystemType-r11 ::= SEQUENCE {
	gps-r11 							ENUMERATED {true}				OPTIONAL,
	glonass-r11							ENUMERATED {true}				OPTIONAL,
	bds-r11								ENUMERATED {true}				OPTIONAL,
	galileo-r11 						ENUMERATED {true}				OPTIONAL,
	wlan-r11							ENUMERATED {true}				OPTIONAL,
	bluetooth-r11						ENUMERATED {true}				OPTIONAL
}

-- ASN1STOP

InDeviceCoexIndication field descriptions
affectedCarrierFreqCombList
Indicates a list of E-UTRA carrier frequencies that are affected by IDC problems due to Inter-Modulation Distortion and harmonics from E-UTRA when configured with UL CA.
affectedCarrierFreqList
List of E-UTRA carrier frequencies affected by IDC problems. 
drx-ActiveTime
Indicates the desired active time that the E-UTRAN is recommended to configure. Value in number of subframes. Value sf20 corresponds to 20 subframes, sf30 corresponds to 30 subframes and so on.
drx-CycleLength
Indicates the desired DRX cycle length that the E-UTRAN is recommended to configure. Value in number of subframes. Value sf40 corresponds to 40 subframes, sf64 corresponds to 64 subframes and so on.
drx-Offset
Indicates the desired DRX starting offset that the E-UTRAN is recommended to configure. The UE shall set the value of drx-Offset smaller than the value of drx-CycleLength. The starting frame and subframe satisfy the relation: [(SFN * 10) + subframe number] modulo (drx-CycleLength) = drx-Offset.
idc-SubframePatternList
A list of one or more subframe patterns indicating which HARQ process E-UTRAN is requested to abstain from using. Value 0 indicates that E-UTRAN is requested to abstain from using the subframe. For FDD, the radio frame in which the pattern starts (i.e. the radio frame in which the first/leftmost bit of the subframePatternFDD corresponds to subframe #0) occurs when SFN mod 2 = 0. For TDD, the first/leftmost bit corresponds to the subframe #0 of the radio frame satisfying SFN mod x = 0, where x is the size of the bit string divided by 10. The UE shall indicate a subframe pattern that follows HARQ time line, as specified in TS 36.213 [23], i.e, if a subframe is set to 1 in the subframe pattern, also the corresponding subframes carrying the potential UL grant [23, 8.0], the UL HARQ retransmission [23, 8.0] and the DL/UL HARQ feedback [23, 7.3, 8.3 and 9.1.2] shall be set to 1.
interferenceDirection
Indicates the direction of IDC interference. Value eutra indicates that only E-UTRA is victim of IDC interference, value other indicates that only another radio is victim of IDC interference and value both indicates that both E-UTRA and another radio are victims of IDC interference. The other radio refers to either the ISM radio or GNSS (see 3GPP TR 36.816 [63]).
victimSystemType
Indicate the list of victim system types to which IDC interference is caused from E-UTRA when configured with UL CA. Value gps, glonass, bds and galileo indicates the type of GNSS. Value wlan indicates WLAN and value bluetooth indicates Bluetooth.

-	InterFreqRSTDMeasurementIndication
The InterFreqRSTDMeasurementIndication message is used to indicate that the UE is going to either start or stop OTDOA inter-frequency RSTD measurement which requires measurement gaps as specified in TS 36.133 [16, 8.1.2.6].
Signalling radio bearer: SRB1
RLC-SAP: AM
Logical channel: DCCH
Direction: UE to E-UTRAN
InterFreqRSTDMeasurementIndication message
-- ASN1START

InterFreqRSTDMeasurementIndication-r10 ::=			SEQUENCE {
	criticalExtensions					CHOICE {
		c1									CHOICE {
			interFreqRSTDMeasurementIndication-r10	InterFreqRSTDMeasurementIndication-r10-IEs,
			spare3 NULL, spare2 NULL, spare1 NULL
		},
		criticalExtensionsFuture			SEQUENCE {}
	}
}

InterFreqRSTDMeasurementIndication-r10-IEs ::=		SEQUENCE {
	rstd-InterFreqIndication-r10		CHOICE {
		start								SEQUENCE {
			rstd-InterFreqInfoList-r10				RSTD-InterFreqInfoList-r10
		},
		stop								NULL
	},
	lateNonCriticalExtension			OCTET STRING						OPTIONAL,
	nonCriticalExtension				SEQUENCE {}							OPTIONAL
}

RSTD-InterFreqInfoList-r10 ::=	SEQUENCE (SIZE(1..maxRSTD-Freq-r10)) OF RSTD-InterFreqInfo-r10

RSTD-InterFreqInfo-r10 ::=		SEQUENCE {
	carrierFreq-r10					ARFCN-ValueEUTRA,
	measPRS-Offset-r10				INTEGER (0..39),
	...,
	[[	carrierFreq-v1090			ARFCN-ValueEUTRA-v9e0				OPTIONAL
	]]
}

-- ASN1STOP

InterFreqRSTDMeasurementIndication field descriptions
carrierFreq
The EARFCN value of the carrier received from upper layers for which the UE needs to perform the inter-frequency RSTD measurements. If the UE includes carrierFreq-v1090, it shall set carrierFreq-r10 to maxEARFCN.
measPRS-Offset
Indicates the requested gap offset for performing inter-frequency RSTD measurements. It is the smallest subframe offset from the beginning of subframe 0 of SFN=0 of the serving cell of the requested gap for measuring PRS positioning occasions in the carrier frequency carrierFreq for which the UE needs to perform the inter-frequency RSTD measurements. The PRS positioning occasion information is received from upper layers. The value of measPRS-Offset is obtained by mapping the starting subframe of the PRS positioning occasion in the measured cell onto the corresponding subframe in the serving cell and is calculated as the serving cell's number of subframes from SFN=0 mod 40.
The UE shall take into account any additional time required by the UE to start PRS measurements on the other carrier when it does this mapping for determining the measPRS-Offset.
NOTE: Figure 6.2.2-1 illustrates the measPRS-Offset field.
rstd-InterFreqIndication
Indicates the inter-frequency RSTD measurement action, i.e. the UE is going to start or stop inter-frequency RSTD measurement.


Figure 6.2.2-1 (informative): Exemplary calculation of measPRS-Offset field.

-	LoggedMeasurementConfiguration
The LoggedMeasurementConfiguration message is used by E-UTRAN to configure the UE to perform logging of measurement results while in RRC_IDLE or to perform logging of measurement results for MBSFN while in both RRC_IDLE and RRC_CONNECTED. It is used to transfer the logged measurement configuration for network performance optimisation, see TS 37.320 [60].
Signalling radio bearer: SRB1
RLC-SAP: AM
Logical channel: DCCH
Direction: E-UTRAN to UE
LoggedMeasurementConfiguration message
-- ASN1START

LoggedMeasurementConfiguration-r10 ::=	SEQUENCE {
	criticalExtensions					CHOICE {
		c1									CHOICE {
			loggedMeasurementConfiguration-r10		LoggedMeasurementConfiguration-r10-IEs,
			spare3 NULL, spare2 NULL, spare1 NULL
		},
		criticalExtensionsFuture				SEQUENCE {}
	}
}


LoggedMeasurementConfiguration-r10-IEs ::= SEQUENCE {		
	traceReference-r10				TraceReference-r10,
	traceRecordingSessionRef-r10	OCTET STRING (SIZE (2)),
	tce-Id-r10						OCTET STRING (SIZE (1)),
	absoluteTimeInfo-r10			AbsoluteTimeInfo-r10,
	areaConfiguration-r10			AreaConfiguration-r10		OPTIONAL,	-- Need OR
	loggingDuration-r10				LoggingDuration-r10,
	loggingInterval-r10				LoggingInterval-r10,
	nonCriticalExtension			LoggedMeasurementConfiguration-v1080-IEs	OPTIONAL
}

LoggedMeasurementConfiguration-v1080-IEs ::= SEQUENCE {
	lateNonCriticalExtension-r10	OCTET STRING						OPTIONAL,
	nonCriticalExtension			LoggedMeasurementConfiguration-v1130-IEs	OPTIONAL
}

LoggedMeasurementConfiguration-v1130-IEs ::= SEQUENCE {
	plmn-IdentityList-r11			PLMN-IdentityList3-r11		OPTIONAL,	-- Need OR
	areaConfiguration-v1130			AreaConfiguration-v1130		OPTIONAL,	-- Need OR
	nonCriticalExtension			LoggedMeasurementConfiguration-v1250-IEs	OPTIONAL
}

LoggedMeasurementConfiguration-v1250-IEs ::= SEQUENCE {
	targetMBSFN-AreaList-r12	TargetMBSFN-AreaList-r12		OPTIONAL,	-- Need OP
	nonCriticalExtension			SEQUENCE {}					OPTIONAL
}

TargetMBSFN-AreaList-r12 ::= 			SEQUENCE (SIZE (0..maxMBSFN-Area)) OF TargetMBSFN-Area-r12

TargetMBSFN-Area-r12 ::=				SEQUENCE {
	mbsfn-AreaId-r12					MBSFN-AreaId-r12		OPTIONAL,	-- Need OR
	carrierFreq-r12						ARFCN-ValueEUTRA-r9,
	...
}

-- ASN1STOP

LoggedMeasurementConfiguration field descriptions
absoluteTimeInfo
Indicates the absolute time in the current cell. 
areaConfiguration
Used to restrict the area in which the UE performs measurement logging to cells broadcasting either one of the included cell identities or one of the included tracking area codes/ identities.
plmn-IdentityList
Indicates a set of PLMNs defining when the UE performs measurement logging as well as the associated status indication and information retrieval i.e. the UE performs these actions when the RPLMN is part of this set of PLMNs.
targetMBSFN-AreaList
Used to indicate logging of MBSFN measurements and further restrict the area and frequencies for which the UE performs measurement logging for MBSFN. If both MBSFN area id and carrier frequency are present, a specific MBSFN area is indicated. If only carrier frequency is present, all MBSFN areas on that carrier frequency are indicated. If there is no entry in the list, any MBSFN area is indicated. 
tce-Id
Parameter Trace Collection Entity Id: See TS 32.422 [58].
traceRecordingSessionRef
Parameter Trace Recording Session Reference: See TS 32.422 [58]

-	MasterInformationBlock
The MasterInformationBlock includes the system information transmitted on BCH.
Signalling radio bearer: N/A
RLC-SAP: TM
Logical channel: BCCH
Direction: E-UTRAN to UE
MasterInformationBlock
-- ASN1START

MasterInformationBlock ::=			SEQUENCE {
	dl-Bandwidth						ENUMERATED {
											n6, n15, n25, n50, n75, n100},
	phich-Config						PHICH-Config,
	systemFrameNumber					BIT STRING (SIZE (8)),
	spare								BIT STRING (SIZE (10))
}


-- ASN1STOP

MasterInformationBlock field descriptions
dl-Bandwidth
Parameter: transmission bandwidth configuration, NRB in downlink, see TS 36.101 [42, table 5.6-1]. n6 corresponds to 6 resource blocks, n15 to 15 resource blocks and so on.
systemFrameNumber
Defines the 8 most significant bits of the SFN. As indicated in TS 36.211 [21, 6.6.1], the 2 least significant bits of the SFN are acquired implicitly in the P-BCH decoding, i.e. timing of 40ms P-BCH TTI indicates 2 least significant bits (within 40ms P-BCH TTI, the first radio frame: 00, the second radio frame: 01, the third radio frame: 10, the last radio frame: 11). One value applies for all serving cells of a Cell Group (i.e. MCG or SCG). The associated functionality is common (i.e. not performed independently for each cell).

-	MBMSCountingRequest
The MBMSCountingRequest message is used by E-UTRAN to count the UEs that are receiving or interested to receive specific MBMS services.
Signalling radio bearer: N/A
RLC-SAP: UM
Logical channel: MCCH
Direction: E-UTRAN to UE
MBMSCountingRequest message
-- ASN1START

MBMSCountingRequest-r10 ::=		SEQUENCE {
	countingRequestList-r10			CountingRequestList-r10,
	lateNonCriticalExtension		OCTET STRING						OPTIONAL,
	nonCriticalExtension			SEQUENCE {}							OPTIONAL
}

CountingRequestList-r10 ::=	SEQUENCE (SIZE (1..maxServiceCount)) OF CountingRequestInfo-r10

CountingRequestInfo-r10 ::=		SEQUENCE {
	tmgi-r10							TMGI-r9,
	...
}

-- ASN1STOP

-	MBMSCountingResponse
The MBMSCountingResponse message is used by the UE to respond to an MBMSCountingRequest message.
Signalling radio bearer: SRB1
RLC-SAP: AM
Logical channel: DCCH
Direction: UE to E-UTRAN
MBMSCountingResponse message
-- ASN1START

MBMSCountingResponse-r10 ::=			SEQUENCE {
	criticalExtensions					CHOICE {
		c1									CHOICE {
			countingResponse-r10				MBMSCountingResponse-r10-IEs,
			spare3 NULL, spare2 NULL, spare1 NULL
		},
		criticalExtensionsFuture			SEQUENCE {}
	}
}

MBMSCountingResponse-r10-IEs ::=	SEQUENCE {
	mbsfn-AreaIndex-r10				INTEGER (0..maxMBSFN-Area-1) 						OPTIONAL,
	countingResponseList-r10		CountingResponseList-r10			OPTIONAL,
	lateNonCriticalExtension		OCTET STRING						OPTIONAL,
	nonCriticalExtension			SEQUENCE {}							OPTIONAL
}

CountingResponseList-r10 ::=		SEQUENCE (SIZE (1..maxServiceCount)) OF CountingResponseInfo-r10

CountingResponseInfo-r10 ::=		SEQUENCE {
	countingResponseService-r10	INTEGER (0..maxServiceCount-1),
	...
}

-- ASN1STOP

MBMSCountingResponse field descriptions
countingResponseList
List of MBMS services which the UE is receiving or interested to receive. Value 0 for field countingResponseService corresponds to the first entry in countingRequestList within MBMSCountingRequest, value 1 corresponds to the second entry in this list and so on.
mbsfn-AreaIndex
Index of the entry in field mbsfn-AreaInfoList within SystemInformationBlockType13. Value 0 corresponds to the first entry in mbsfn-AreaInfoList within SystemInformationBlockType13, value 1 corresponds to the second entry in this list and so on.

-	MBMSInterestIndication
The MBMSInterestIndication message is used to inform E-UTRAN that the UE is receiving/ interested to receive or no longer receiving/ interested to receive MBMS via an (SC-)MRB.
Signalling radio bearer: SRB1
RLC-SAP: AM
Logical channel: DCCH
Direction: UE to E-UTRAN
MBMSInterestIndication message
-- ASN1START

MBMSInterestIndication-r11 ::=		SEQUENCE {
	criticalExtensions					CHOICE {
		c1									CHOICE {
			interestIndication-r11				MBMSInterestIndication-r11-IEs,
			spare3 NULL, spare2 NULL, spare1 NULL
		},
		criticalExtensionsFuture			SEQUENCE {}
	}
}

MBMSInterestIndication-r11-IEs ::=	SEQUENCE {
	mbms-FreqList-r11					CarrierFreqListMBMS-r11			OPTIONAL,
	mbms-Priority-r11					ENUMERATED {true}				OPTIONAL,
	lateNonCriticalExtension			OCTET STRING					OPTIONAL,
	nonCriticalExtension				MBMSInterestIndication-r13-IEs	OPTIONAL
}

MBMSInterestIndication-r13-IEs ::=	SEQUENCE {
	mbms-Services-r13					MBMSServiceList-r13				OPTIONAL,
	nonCriticalExtension				SEQUENCE {}						OPTIONAL
}

-- ASN1STOP

MBMSInterestIndication field descriptions
mbms-FreqList
List of MBMS frequencies on which the UE is receiving or interested to receive MBMS via an (SC-)MRB.
mbms-Priority
Indicates whether the UE prioritises MBMS reception above unicast reception. The field is present (i.e. value true), if the UE prioritises reception of all listed MBMS frequencies above reception of any of the unicast bearers. Otherwise the field is absent.

-	MBSFNAreaConfiguration
The MBSFNAreaConfiguration message contains the MBMS control information applicable for an MBSFN area. For each MBSFN area included in SystemInformationBlockType13 E-UTRAN configures an MCCH (i.e. the MCCH identifies the MBSFN area) and signals the MBSFNAreaConfiguration message.
Signalling radio bearer: N/A
RLC-SAP: UM
Logical channel: MCCH
Direction: E-UTRAN to UE
MBSFNAreaConfiguration message
-- ASN1START

MBSFNAreaConfiguration-r9 ::=		SEQUENCE {
	commonSF-Alloc-r9					CommonSF-AllocPatternList-r9,
	commonSF-AllocPeriod-r9				ENUMERATED {
												rf4, rf8, rf16, rf32, rf64, rf128, rf256},
	pmch-InfoList-r9					PMCH-InfoList-r9,
	nonCriticalExtension				MBSFNAreaConfiguration-v930-IEs	OPTIONAL
}

MBSFNAreaConfiguration-v930-IEs ::= SEQUENCE {
	lateNonCriticalExtension			OCTET STRING						OPTIONAL,
	nonCriticalExtension				MBSFNAreaConfiguration-v1250-IEs		OPTIONAL
}

MBSFNAreaConfiguration-v1250-IEs ::= SEQUENCE {
	pmch-InfoListExt-r12				PMCH-InfoListExt-r12 				OPTIONAL, 	-- Need OR
	nonCriticalExtension				SEQUENCE {}							OPTIONAL
}

CommonSF-AllocPatternList-r9 ::=	SEQUENCE (SIZE (1..maxMBSFN-Allocations)) OF MBSFN-SubframeConfig

-- ASN1STOP

MBSFNAreaConfiguration field descriptions
commonSF-Alloc
Indicates the subframes allocated to the MBSFN area. E-UTRAN always sets this field to cover at least the subframes configured by SystemInformationBlockType13 for this MCCH, regardless of whether any MBMS sessions are ongoing.
commonSF-AllocPeriod
Indicates the period during which resources corresponding with field commonSF-Alloc are divided between the (P)MCH that are configured for this MBSFN area. The subframe allocation patterns, as defined by commonSF-Alloc, repeat continously during this period. Value rf4 corresponds to 4 radio frames, rf8 corresponds to 8 radio frames and so on. The commonSF-AllocPeriod starts in the radio frames for which: SFN mod commonSF-AllocPeriod = 0.
pmch-InfoList
EUTRAN may include pmch-InfoListExt even if pmch-InfoList does not include maxPMCH-PerMBSFN entries. EUTRAN configures at most maxPMCH-PerMBSFN entries i.e. across pmch-InfoList and pmch-InfoListExt.

-	MeasurementReport
The MeasurementReport message is used for the indication of measurement results.
Signalling radio bearer: SRB1
RLC-SAP: AM
Logical channel: DCCH
Direction: UE to E-UTRAN
MeasurementReport message
-- ASN1START

MeasurementReport ::=				SEQUENCE {
	criticalExtensions					CHOICE {
		c1									CHOICE{
			measurementReport-r8				MeasurementReport-r8-IEs,
			spare7 NULL,
			spare6 NULL, spare5 NULL, spare4 NULL,
			spare3 NULL, spare2 NULL, spare1 NULL
		},
		criticalExtensionsFuture			SEQUENCE {}
	}
}

MeasurementReport-r8-IEs ::=		SEQUENCE {
	measResults							MeasResults,
	nonCriticalExtension				MeasurementReport-v8a0-IEs							OPTIONAL
}

MeasurementReport-v8a0-IEs ::= SEQUENCE {
	lateNonCriticalExtension			OCTET STRING						OPTIONAL,
	nonCriticalExtension				SEQUENCE {}							OPTIONAL
}

-- ASN1STOP

-	MobilityFromEUTRACommand
The MobilityFromEUTRACommand message is used to command handover or a cell change from E-UTRA to another RAT (3GPP or non-3GPP), or enhanced CS fallback to CDMA2000 1xRTT.
Signalling radio bearer: SRB1
RLC-SAP: AM
Logical channel: DCCH
Direction: E-UTRAN to UE
MobilityFromEUTRACommand message
-- ASN1START

MobilityFromEUTRACommand ::=		SEQUENCE {
	rrc-TransactionIdentifier			RRC-TransactionIdentifier,
	criticalExtensions					CHOICE {
		c1									CHOICE{
			mobilityFromEUTRACommand-r8		MobilityFromEUTRACommand-r8-IEs,
			mobilityFromEUTRACommand-r9 		MobilityFromEUTRACommand-r9-IEs,
			spare2 NULL, spare1 	NULL
		},
		criticalExtensionsFuture			SEQUENCE {}
	}
}

MobilityFromEUTRACommand-r8-IEs ::=	SEQUENCE {
	cs-FallbackIndicator				BOOLEAN,
	purpose								CHOICE{
		handover							Handover,
		cellChangeOrder						CellChangeOrder
	},
	nonCriticalExtension				MobilityFromEUTRACommand-v8a0-IEs	OPTIONAL
}

MobilityFromEUTRACommand-v8a0-IEs ::= SEQUENCE {
	lateNonCriticalExtension			OCTET STRING						OPTIONAL,
	nonCriticalExtension				MobilityFromEUTRACommand-v8d0-IEs	OPTIONAL
}

MobilityFromEUTRACommand-v8d0-IEs ::= SEQUENCE {
	bandIndicator						BandIndicatorGERAN			OPTIONAL,	-- Cond GERAN
	nonCriticalExtension				SEQUENCE {}					OPTIONAL
}

MobilityFromEUTRACommand-r9-IEs ::=	SEQUENCE {
	cs-FallbackIndicator				BOOLEAN,
	purpose								CHOICE{
		handover							Handover,
		cellChangeOrder						CellChangeOrder,
		e-CSFB-r9							E-CSFB-r9,
		...
	},
	nonCriticalExtension				MobilityFromEUTRACommand-v930-IEs	OPTIONAL
}

MobilityFromEUTRACommand-v930-IEs ::= SEQUENCE {
	lateNonCriticalExtension			OCTET STRING						OPTIONAL,
	nonCriticalExtension				MobilityFromEUTRACommand-v960-IEs	OPTIONAL
}

MobilityFromEUTRACommand-v960-IEs ::= SEQUENCE {
	bandIndicator						BandIndicatorGERAN			OPTIONAL,	-- Cond GERAN
	nonCriticalExtension				SEQUENCE {}					OPTIONAL
}

Handover ::=						SEQUENCE {
	targetRAT-Type						ENUMERATED {
											utra, geran, cdma2000-1XRTT, cdma2000-HRPD,
											spare4,	spare3, spare2, spare1, ...},
	targetRAT-MessageContainer			OCTET STRING,
	nas-SecurityParamFromEUTRA			OCTET STRING (SIZE (1)) 	OPTIONAL,	-- Cond UTRAGERAN
	systemInformation					SI-OrPSI-GERAN				OPTIONAL	-- Cond PSHO
}

CellChangeOrder ::=				SEQUENCE {
	t304								ENUMERATED {
											ms100, ms200, ms500, ms1000,
											ms2000, ms4000, ms8000, spare1},
	targetRAT-Type						CHOICE {
			geran							SEQUENCE {
				physCellId						PhysCellIdGERAN,
				carrierFreq						CarrierFreqGERAN,
				networkControlOrder				BIT STRING (SIZE (2)) 		OPTIONAL,	-- Need OP
				systemInformation				SI-OrPSI-GERAN				OPTIONAL	-- Need OP
			},
			...
	}
}

SI-OrPSI-GERAN ::=					CHOICE {
	si									SystemInfoListGERAN,
	psi									SystemInfoListGERAN
}

E-CSFB-r9 ::=						SEQUENCE {
	messageContCDMA2000-1XRTT-r9		OCTET STRING		OPTIONAL, 	-- Need ON
	mobilityCDMA2000-HRPD-r9			ENUMERATED {
											handover, redirection 
										}					OPTIONAL,	-- Need OP
	messageContCDMA2000-HRPD-r9		OCTET STRING		OPTIONAL, 	-- Cond concHO
	redirectCarrierCDMA2000-HRPD-r9	CarrierFreqCDMA2000	OPTIONAL	-- Cond concRedir
}

-- ASN1STOP

MobilityFromEUTRACommand field descriptions
bandIndicator
Indicates how to interpret the ARFCN of the BCCH carrier.
carrierFreq
contains the carrier frequency of the target GERAN cell.
cs-FallbackIndicator
Value true indicates that the CS Fallback procedure to UTRAN or GERAN is triggered.
messageContCDMA2000-1XRTT
This field contains a message specified in CDMA2000 1xRTT standard that either tells the UE to move to specific 1xRTT target cell(s) or indicates a failure to allocate resources for the enhanced CS fallback to CDMA2000 1xRTT.
messageContCDMA2000-HRPD
This field contains a message specified in CDMA2000 HRPD standard that either tells the UE to move to specific HRPD target cell(s) or indicates a failure to allocate resources for the handover to CDMA2000 HRPD.
mobilityCDMA2000-HRPD
This field indicates whether or not mobility to CDMA2000 HRPD is to be performed by the UE and it also indicates the type of mobility to CDMA2000 HRPD that is to be performed; If this field is not present the UE shall perform only the enhanced CS fallback to CDMA2000 1xRTT.
nas-SecurityParamFromEUTRA
Used to deliver the key synchronisation and Key freshness for the E-UTRAN to UTRAN handovers as specified in TS 33.401. The content of the parameter is defined in TS24.301.
networkControlOrder
Parameter NETWORK_CONTROL_ORDER in TS 44.060 [36].
purpose
Indicates which type of mobility procedure the UE is requested to perform. EUTRAN always applies value e-CSFB in case of enhanced CS fallback to CDMA2000 (e.g. also when that procedure results in handover to CDMA2000 1XRTT only, in handover to CDMA2000 HRPD only or in redirection to CDMA2000 HRPD only),
redirectCarrierCDMA2000-HRPD
The redirectCarrierCDMA2000-HRPD indicates a CDMA2000 carrier frequency and is used to redirect the UE to a HRPD carrier frequency.
SystemInfoListGERAN
If purpose = CellChangeOrder and if the field is not present, the UE has to acquire SI/PSI from the GERAN cell.
t304
Timer T304 as described in section 7.3. Value ms100 corresponds with 100 ms, ms200 corresponds with 200 ms and so on.
targetRAT-Type
Indicates the target RAT type.
targetRAT-MessageContainer
The field contains a message specified in another standard, as indicated by the targetRAT-Type, and carries information about the target cell identifier(s) and radio parameters relevant for the target radio access technology. NOTE 1.

A complete message is included, as specified in the other standard.

Conditional presence
Explanation
concHO
The field is mandatory present if the mobilityCDMA2000-HRPD is set to "handover"; otherwise the field is optional present, need ON.
concRedir
The field is mandatory present if the mobilityCDMA2000-HRPD is set to "redirection"; otherwise the field is not present.
GERAN
The field should be present if the purpose is set to "handover" and the targetRAT-Type is set to "geran"; otherwise the field is not present
PSHO
The field is mandatory present in case of PS handover toward GERAN; otherwise the field is optionally present, but not used by the UE
UTRAGERAN
The field is mandatory present if the targetRAT-Type is set to "utra" or "geran"; otherwise the field is not present

NOTE 1:	The correspondence between the value of the targetRAT-Type, the standard to apply and the message contained within the targetRAT-MessageContainer is shown in the table below:
targetRAT-Type
Standard to apply
targetRAT-MessageContainer
cdma2000-1XRTT
C.S0001 or later, C.S0007 or later, C.S0008 or later

cdma2000-HRPD
C.S0024 or later

geran
GSM TS 04.18, version 8.5.0 or later, or 3GPP TS 44.018 (clause 9.1.15)

3GPP TS 44.060, version 6.13.0 or later (clause 11.2.43)

3GPP TS 44.060, version 7.6.0 or later (clause 11.2.46)
HANDOVER COMMAND


PS HANDOVER COMMAND


DTM HANDOVER COMMAND
utra
3GPP TS 25.331 (clause 10.2.16a)
Handover TO UTRAN command

-	Paging
The Paging message is used for the notification of one or more UEs.
Signalling radio bearer: N/A
RLC-SAP: TM
Logical channel: PCCH
Direction: E-UTRAN to UE
Paging message
-- ASN1START

Paging ::=					SEQUENCE {
	pagingRecordList				PagingRecordList 					OPTIONAL,	-- Need ON
	systemInfoModification			ENUMERATED {true}					OPTIONAL,	-- Need ON
	etws-Indication					ENUMERATED {true}					OPTIONAL,	-- Need ON
	nonCriticalExtension			Paging-v890-IEs						OPTIONAL
}

Paging-v890-IEs ::=			SEQUENCE {
	lateNonCriticalExtension		OCTET STRING							OPTIONAL,
	nonCriticalExtension			Paging-v920-IEs							OPTIONAL
}

Paging-v920-IEs ::=			SEQUENCE {
	cmas-Indication-r9				ENUMERATED {true}					OPTIONAL,	-- Need ON
	nonCriticalExtension				Paging-v1130-IEs				OPTIONAL
}

Paging-v1130-IEs ::=			SEQUENCE {
	eab-ParamModification-r11		ENUMERATED {true}					OPTIONAL,	-- Need ON
	nonCriticalExtension			Paging-v13xx-IEs					OPTIONAL
}

Paging-v13xx-IEs ::=			SEQUENCE {
	redistributionIndication-r13	ENUMERATED {true}					OPTIONAL,	--Need ON
	systemInfoModification-eDRX-r13	ENUMERATED {true}					OPTIONAL,	-- Need ON
	nonCriticalExtension			SEQUENCE {}							OPTIONAL
}

PagingRecordList ::=				SEQUENCE (SIZE (1..maxPageRec)) OF PagingRecord

PagingRecord ::=					SEQUENCE {
	ue-Identity							PagingUE-Identity,
	cn-Domain							ENUMERATED	{ps, cs},
	...
}

PagingUE-Identity ::=				CHOICE {
	s-TMSI								S-TMSI,
	imsi								IMSI,
	...
}

IMSI ::=							SEQUENCE (SIZE (6..21)) OF IMSI-Digit

IMSI-Digit ::=						INTEGER (0..9)

-- ASN1STOP

Paging field descriptions
cmas-Indication
If present: indication of a CMAS notification.
cn-Domain
Indicates the origin of paging.
eab-ParamModification
If present: indication of an EAB parameters (SIB14) modification.
etws-Indication
If present: indication of an ETWS primary notification and/ or ETWS secondary notification.
imsi
The International Mobile Subscriber Identity, a globally unique permanent subscriber identity, see TS 23.003 [27]. The first element contains the first IMSI digit, the second element contains the second IMSI digit and so on.
redistributionIndication
If present: indication to trigger E-UTRAN Inter-frequency Redistribution procedure as specified in 5.2.4.10 [4]
systemInfoModification
If present: indication of a BCCH modification other than SIB10, SIB11, SIB12 and SIB14.
systemInfoModification-eDRX
If present: indication of a BCCH modification other than SIB10, SIB11, SIB12 and SIB14 for UEs in extended DRX. This indication applies only to UEs having eDRX cycle longer than the BCCH modification period.
ue-Identity
Provides the NAS identity of the UE that is being paged.

-	ProximityIndication
The ProximityIndication message is used to indicate that the UE is entering or leaving the proximity of one or more CSG member cell(s).
Signalling radio bearer: SRB1
RLC-SAP: AM
Logical channel: DCCH
Direction: UE to E-UTRAN
ProximityIndication message
-- ASN1START

ProximityIndication-r9 ::= SEQUENCE {
	criticalExtensions					CHOICE {
		c1									CHOICE {
			proximityIndication-r9				ProximityIndication-r9-IEs,
			spare3 NULL, spare2 NULL, spare1 NULL
			},
		criticalExtensionsFuture			SEQUENCE {}
	}
}

ProximityIndication-r9-IEs ::= SEQUENCE {
	type-r9								ENUMERATED {entering, leaving},
	carrierFreq-r9						CHOICE {
		eutra-r9							ARFCN-ValueEUTRA,
		utra-r9								ARFCN-ValueUTRA,
		...,
		eutra2-v9e0							ARFCN-ValueEUTRA-v9e0
	},
	nonCriticalExtension				ProximityIndication-v930-IEs							OPTIONAL
}

ProximityIndication-v930-IEs ::= SEQUENCE {
	lateNonCriticalExtension			OCTET STRING						OPTIONAL,
	nonCriticalExtension				SEQUENCE {}							OPTIONAL
}

-- ASN1STOP

ProximityIndication field descriptions
carrierFreq
Indicates the RAT and frequency of the CSG member cell(s), for which the proximity indication is sent. For E-UTRA and UTRA frequencies, the UE shall set the ARFCN according to a band it previously considered suitable for accessing (one of) the CSG member cell(s), for which the proximity indication is sent.
type
Used to indicate whether the UE is entering or leaving the proximity of CSG member cell(s).

-	RNReconfiguration
The RNReconfiguration is a command to modify the RN subframe configuration and/or to convey changed system information.
Signalling radio bearer: SRB1
RLC-SAP: AM
Logical channel: DCCH
Direction: E-UTRAN to RN
RNReconfiguration message
-- ASN1START

RNReconfiguration-r10 ::=		SEQUENCE {
	rrc-TransactionIdentifier		RRC-TransactionIdentifier,
	criticalExtensions				CHOICE {
		c1								CHOICE {
			rnReconfiguration-r10		RNReconfiguration-r10-IEs, 
			spare3 NULL, spare2 NULL, spare1 NULL
		},
		criticalExtensionsFuture		SEQUENCE {}
	}
}

RNReconfiguration-r10-IEs ::=		SEQUENCE {
	rn-SystemInfo-r10					RN-SystemInfo-r10			OPTIONAL,	-- Need ON
	rn-SubframeConfig-r10				RN-SubframeConfig-r10			OPTIONAL,	-- Need ON
	lateNonCriticalExtension			OCTET STRING					OPTIONAL,
	nonCriticalExtension				SEQUENCE {}						OPTIONAL
}

RN-SystemInfo-r10 ::=			SEQUENCE {
	systemInformationBlockType1-r10		OCTET STRING (CONTAINING SystemInformationBlockType1)	OPTIONAL,	-- Need ON
	systemInformationBlockType2-r10		SystemInformationBlockType2		OPTIONAL,	-- Need ON
	...
}

-- ASN1STOP

-	RNReconfigurationComplete
The RNReconfigurationComplete message is used to confirm the successful completion of an RN reconfiguration.
Signalling radio bearer: SRB1
RLC-SAP: AM
Logical channel: DCCH
Direction: RN to E-UTRAN
RNReconfigurationComplete message
-- ASN1START

RNReconfigurationComplete-r10 ::=		SEQUENCE {
	rrc-TransactionIdentifier				RRC-TransactionIdentifier,
	criticalExtensions						CHOICE {
		c1										CHOICE{
			rnReconfigurationComplete-r10			RNReconfigurationComplete-r10-IEs,
			spare3 NULL, spare2 NULL, spare1 NULL
		},
		criticalExtensionsFuture				SEQUENCE {}
	}
}

RNReconfigurationComplete-r10-IEs ::=	SEQUENCE {
	lateNonCriticalExtension				OCTET STRING				OPTIONAL,
	nonCriticalExtension					SEQUENCE {}					OPTIONAL
}

-- ASN1STOP

-	RRCConnectionReconfiguration
The RRCConnectionReconfiguration message is the command to modify an RRC connection. It may convey information for measurement configuration, mobility control, radio resource configuration (including RBs, MAC main configuration and physical channel configuration) including any associated dedicated NAS information and security configuration.
Signalling radio bearer: SRB1
RLC-SAP: AM
Logical channel: DCCH
Direction: E-UTRAN to UE
RRCConnectionReconfiguration message
-- ASN1START

RRCConnectionReconfiguration ::=	SEQUENCE {
	rrc-TransactionIdentifier			RRC-TransactionIdentifier,
	criticalExtensions					CHOICE {
		c1									CHOICE{
			rrcConnectionReconfiguration-r8		RRCConnectionReconfiguration-r8-IEs,
			spare7 NULL,
			spare6 NULL, spare5 NULL, spare4 NULL,
			spare3 NULL, spare2 NULL, spare1 NULL
		},
		criticalExtensionsFuture			SEQUENCE {}
	}
}

RRCConnectionReconfiguration-r8-IEs ::= SEQUENCE {
	measConfig							MeasConfig						OPTIONAL,	-- Need ON
	mobilityControlInfo					MobilityControlInfo				OPTIONAL,	-- Cond HO
	dedicatedInfoNASList				SEQUENCE (SIZE(1..maxDRB)) OF
											DedicatedInfoNAS			OPTIONAL,	-- Cond nonHO
	radioResourceConfigDedicated		RadioResourceConfigDedicated	OPTIONAL, -- Cond HO-toEUTRA
	securityConfigHO					SecurityConfigHO				OPTIONAL,	-- Cond HO
	nonCriticalExtension				RRCConnectionReconfiguration-v890-IEs	OPTIONAL
}

RRCConnectionReconfiguration-v890-IEs ::= SEQUENCE {
	lateNonCriticalExtension			OCTET STRING (CONTAINING RRCConnectionReconfiguration-v8m0-IEs)	OPTIONAL,
	nonCriticalExtension				RRCConnectionReconfiguration-v920-IEs	OPTIONAL
}

-- Late non-critical extensions:
RRCConnectionReconfiguration-v8m0-IEs ::= SEQUENCE {
	-- Following field is only for pre REL-10 late non-critical extensions
	lateNonCriticalExtension			OCTET STRING					OPTIONAL, 
	nonCriticalExtension				RRCConnectionReconfiguration-v10i0-IEs		OPTIONAL
}

RRCConnectionReconfiguration-v10i0-IEs ::= SEQUENCE {
	antennaInfoDedicatedPCell-v10i0		AntennaInfoDedicated-v10i0			OPTIONAL,	-- Need ON
	-- Following field is only for late non-critical extensions from REL-10
	nonCriticalExtension				SEQUENCE {}				OPTIONAL
}

-- Regular non-critical extensions:
RRCConnectionReconfiguration-v920-IEs ::= SEQUENCE {
	otherConfig-r9						OtherConfig-r9					OPTIONAL,	-- Need ON
	fullConfig-r9						ENUMERATED {true}				OPTIONAL,	-- Cond HO-Reestab
	nonCriticalExtension				RRCConnectionReconfiguration-v1020-IEs	OPTIONAL
}

RRCConnectionReconfiguration-v1020-IEs ::= SEQUENCE {
	sCellToReleaseList-r10				SCellToReleaseList-r10			OPTIONAL,	-- Need ON
	sCellToAddModList-r10				SCellToAddModList-r10			OPTIONAL,	-- Need ON
	nonCriticalExtension				RRCConnectionReconfiguration-v1130-IEs	OPTIONAL
}

RRCConnectionReconfiguration-v1130-IEs ::= SEQUENCE {
	systemInfomationBlockType1Dedicated-r11	OCTET STRING (CONTAINING SystemInformationBlockType1)																			OPTIONAL,	-- Need ON
	nonCriticalExtension				RRCConnectionReconfiguration-v1250-IEs	OPTIONAL
}

RRCConnectionReconfiguration-v1250-IEs ::= SEQUENCE {
	wlan-OffloadInfo-r12				CHOICE {
		release 								NULL,
		setup									SEQUENCE {
			wlan-OffloadConfigDedicated-r12		WLAN-OffloadConfig-r12,
			t350-r12								ENUMERATED {min5, min10, min20, min30, min60,
												 min120, min180, spare1}	OPTIONAL	-- Need OR
		}
	}																	OPTIONAL,		-- Need ON
	scg-Configuration-r12				SCG-Configuration-r12		OPTIONAL, 	-- Cond nonFullConfig
	sl-SyncTxControl-r12				SL-SyncTxControl-r12			OPTIONAL,	-- Need ON
	sl-DiscConfig-r12					SL-DiscConfig-r12				OPTIONAL,	-- Need ON
	sl-CommConfig-r12					SL-CommConfig-r12				OPTIONAL,	-- Need ON
	nonCriticalExtension				RRCConnectionReconfiguration-v13xy-IEs	OPTIONAL
}

RRCConnectionReconfiguration-v13xy-IEs ::= SEQUENCE {
	sCellToReleaseListExt-r13			SCellToReleaseListExt-r13		OPTIONAL,	-- Need ON
	sCellToAddModListExt-r13			SCellToAddModListExt-r13		OPTIONAL,	-- Need ON
	nonCriticalExtension				SEQUENCE {}						OPTIONAL
}

SL-SyncTxControl-r12 ::=			SEQUENCE {
	networkControlledSyncTx-r12				ENUMERATED {on, off}		OPTIONAL		-- Need OP
}

PSCellToAddMod-r12 ::=				SEQUENCE {
	sCellIndex-r12						SCellIndex-r10,
	cellIdentification-r12				SEQUENCE {
		physCellId-r12						PhysCellId,
		dl-CarrierFreq-r12					ARFCN-ValueEUTRA-r9
	}																	OPTIONAL,	-- Cond SCellAdd
	radioResourceConfigCommonPSCell-r12		RadioResourceConfigCommonPSCell-r12	OPTIONAL,	-- Cond SCellAdd
	radioResourceConfigDedicatedPSCell-r12	RadioResourceConfigDedicatedPSCell-r12	OPTIONAL,	-- Cond SCellAdd2
	...,
	[[	antennaInfoDedicatedPSCell-v1280		AntennaInfoDedicated-v10i0	OPTIONAL	-- Need ON
	]],
	[[	sCellIndex-r13					SCellIndex-r13	OPTIONAL		-- Need ON
	]]
}

PowerCoordinationInfo-r12 ::= SEQUENCE {
	p-MeNB-r12							INTEGER (1..16),
	p-SeNB-r12							INTEGER (1..16),
	powerControlMode-r12				INTEGER (1..2)
}

SCellToAddModList-r10 ::=		SEQUENCE (SIZE (1..maxSCell-r10)) OF SCellToAddMod-r10

SCellToAddModListExt-r13 ::=	SEQUENCE (SIZE (maxSCell-Plus1..maxSCell-r13)) OF SCellToAddMod-r13

SCellToAddMod-r10 ::=			SEQUENCE {
	sCellIndex-r10						SCellIndex-r10,
	cellIdentification-r10				SEQUENCE {
		physCellId-r10						PhysCellId,
		dl-CarrierFreq-r10					ARFCN-ValueEUTRA
	}																OPTIONAL,	-- Cond SCellAdd
	radioResourceConfigCommonSCell-r10		RadioResourceConfigCommonSCell-r10	OPTIONAL,	-- Cond SCellAdd
	radioResourceConfigDedicatedSCell-r10	RadioResourceConfigDedicatedSCell-r10	OPTIONAL,	-- Cond SCellAdd2
	...,
	[[	dl-CarrierFreq-v1090				ARFCN-ValueEUTRA-v9e0	OPTIONAL	-- Cond EARFCN-max
	]],
	[[	antennaInfoDedicatedSCell-v10i0		AntennaInfoDedicated-v10i0	OPTIONAL	-- Need ON
	]]
}

SCellToAddMod-r13 ::=			SEQUENCE {
	sCellIndex-v13xy						SCellIndex-v13xy,
	cellIdentification-r13				SEQUENCE {
		physCellId-r13						PhysCellId,
		dl-CarrierFreq-r13					ARFCN-ValueEUTRA-r9
	}																OPTIONAL,	-- Cond SCellAdd
	radioResourceConfigCommonSCell-r13		RadioResourceConfigCommonSCell-r10	OPTIONAL,	-- Cond SCellAdd
	radioResourceConfigDedicatedSCell-r13	RadioResourceConfigDedicatedSCell-r10	OPTIONAL	-- Cond SCellAdd2
}

SCellToReleaseList-r10 ::=			SEQUENCE (SIZE (1..maxSCell-r10)) OF SCellIndex-r10

SCellToReleaseListExt-r13 ::=			SEQUENCE (SIZE (maxSCell-Plus1..maxSCell-r13)) OF SCellIndex-v13xy

SCG-Configuration-r12 ::=			CHOICE {
	release								NULL,
	setup								SEQUENCE {
		scg-ConfigPartMCG-r12				SEQUENCE {
			scg-Counter-r12						INTEGER (0.. 65535)			OPTIONAL,	-- Need ON
			powerCoordinationInfo-r12			PowerCoordinationInfo-r12	OPTIONAL,	-- Need ON
			...
		}																OPTIONAL,	-- Need ON
		scg-ConfigPartSCG-r12				SCG-ConfigPartSCG-r12 		OPTIONAL	-- Need ON
	}
}

SCG-ConfigPartSCG-r12 ::=			SEQUENCE {
	radioResourceConfigDedicatedSCG-r12	RadioResourceConfigDedicatedSCG-r12	OPTIONAL,	-- Need ON
	sCellToReleaseListSCG-r12			SCellToReleaseList-r10		OPTIONAL,	-- Need ON
	pSCellToAddMod-r12					PSCellToAddMod-r12			OPTIONAL,	-- Need ON
	sCellToAddModListSCG-r12			SCellToAddModList-r10		OPTIONAL,	-- Need ON
	mobilityControlInfoSCG-r12			MobilityControlInfoSCG-r12	OPTIONAL,	-- Need ON
	...,
	[[
	sCellToReleaseListSCG-Ext-r13			SCellToReleaseListExt-r13		OPTIONAL,	-- Need ON
	sCellToAddModListSCG-Ext-r13				SCellToAddModListExt-r13	OPTIONAL	-- Need ON
	]]
}

SecurityConfigHO ::=				SEQUENCE {
	handoverType						CHOICE {
		intraLTE							SEQUENCE {
			securityAlgorithmConfig				SecurityAlgorithmConfig		OPTIONAL,	-- Cond fullConfig
			keyChangeIndicator					BOOLEAN,
			nextHopChainingCount				NextHopChainingCount
		},
		interRAT							SEQUENCE {
			securityAlgorithmConfig				SecurityAlgorithmConfig,
			nas-SecurityParamToEUTRA			OCTET STRING (SIZE(6))
		}
	},
	...
}


-- ASN1STOP

RRCConnectionReconfiguration field descriptions
dedicatedInfoNASList
This field is used to transfer UE specific NAS layer information between the network and the UE. The RRC layer is transparent for each PDU in the list.
fullConfig
Indicates the full configuration option is applicable for the RRC Connection Reconfiguration message.
keyChangeIndicator
true is used only in an intra-cell handover when a KeNB key is derived from a KASME key taken into use through the latest successful NAS SMC procedure, as described in TS 33.401 [32] for KeNB re-keying. false is used in an intra-LTE handover when the new KeNB key is obtained from the current KeNB key or from the NH as described in TS 33.401 [32].
nas-securityParamToEUTRA
This field is used to transfer UE specific NAS layer information between the network and the UE. The RRC layer is transparent for this field, although it affects activation of AS- security after inter-RAT handover to E-UTRA. The content is defined in TS 24.301.
networkControlledSyncTx
This field indicates whether the UE shall transmit synchronisation information (i.e. become synchronisation source). Value On indicates the UE to transmit synchronisation information while value Off indicates the UE to not transmit such information.
nextHopChainingCount
Parameter NCC: See TS 33.401 [32]
p-MeNB
Indicates the guaranteed power for the MeNB, as specified in 36.213 [23].
powerControlMode
Indicates the power control mode used in DC. Value 1 corresponds to DC power control mode 1 and value 2 indicates DC power control mode 2, as specified in 36.213 [23].
p-SeNB
Indicates the guaranteed power for the SeNB as specified in 36.213 [23, Table 5.1.4.2-1].
sCellIndex
In case of DC, the SCellIndex is unique within the scope of the UE i.e. an SCG cell can not use the same value as used for an MCG cell. For PSCellToAddMod, if sCellIndex-r13 is present, sCellIndex-r12 shall be ignored.
sCellToAddModListSCG
Indicates the SCG cell to be added or modified. The field is used for SCG cells other than the PSCell (which is added/ modified by field pSCellToAddMod).
sCellToReleaseListSCG
Indicates the SCG cell to be released. The field is also used to release the PSCell e.g. upon change of PSCell, upon system information change for the PSCell.
scg-Counter
A counter used upon initial configuration of SCG security as well as upon refresh of S-KeNB. E-UTRAN includes the field upon SCG change when one or more SCG DRBs are configured. Otherwise E-UTRAN does not include the field.
t350
Timer T350 as described in section 7.3. Value minN corresponds to N minutes.

Conditional presence
Explanation
EARFCN-max
The field is mandatory present if dl-CarrierFreq-r10 is included and set to maxEARFCN. Otherwise the field is not present.
fullConfig
This field is mandatory present for handover within E-UTRA when the fullConfig is included; otherwise it is optionally present, Need OP. 
HO
The field is mandatory present in case of handover within E-UTRA or to E-UTRA; otherwise the field is not present.
HO-Reestab
This field is optionally present, need ON, in case of handover within E-UTRA or upon the first reconfiguration after RRC connection re-establishment; otherwise the field is not present.
HO-toEUTRA
The field is mandatory present in case of handover to E-UTRA or for reconfigurations when fullConfig is included; otherwise the field is optionally present, need ON.
nonFullConfig
The field is not present in case of handover within E-UTRA when the fullConfig is included or in case of handover to E-UTRA; otherwise it is optional present, need ON.
nonHO
The field is not present in case of handover within E-UTRA or to E-UTRA; otherwise it is optional present, need ON.
SCellAdd
The field is mandatory present upon SCell addition; otherwise it is not present.
SCellAdd2
The field is mandatory present upon SCell addition; otherwise it is optionally present, need ON.

-	RRCConnectionReconfigurationComplete
The RRCConnectionReconfigurationComplete message is used to confirm the successful completion of an RRC connection reconfiguration.
Signalling radio bearer: SRB1
RLC-SAP: AM
Logical channel: DCCH
Direction: UE to E-UTRAN
RRCConnectionReconfigurationComplete message
-- ASN1START

RRCConnectionReconfigurationComplete ::= SEQUENCE {
	rrc-TransactionIdentifier			RRC-TransactionIdentifier,
	criticalExtensions					CHOICE {
		rrcConnectionReconfigurationComplete-r8
											RRCConnectionReconfigurationComplete-r8-IEs,
		criticalExtensionsFuture			SEQUENCE {}
	}
}

RRCConnectionReconfigurationComplete-r8-IEs ::= SEQUENCE {
	nonCriticalExtension				RRCConnectionReconfigurationComplete-v8a0-IEs	OPTIONAL
}

RRCConnectionReconfigurationComplete-v8a0-IEs ::= SEQUENCE {
	lateNonCriticalExtension			OCTET STRING						OPTIONAL,
	nonCriticalExtension				RRCConnectionReconfigurationComplete-v1020-IEs	OPTIONAL
}

RRCConnectionReconfigurationComplete-v1020-IEs ::= SEQUENCE {
	rlf-InfoAvailable-r10				ENUMERATED {true}				OPTIONAL,
	logMeasAvailable-r10				ENUMERATED {true}				OPTIONAL,
	nonCriticalExtension				RRCConnectionReconfigurationComplete-v1130-IEs	OPTIONAL
}

RRCConnectionReconfigurationComplete-v1130-IEs ::= SEQUENCE {
	connEstFailInfoAvailable-r11		ENUMERATED {true}				OPTIONAL,
	nonCriticalExtension				RRCConnectionReconfigurationComplete-v1250-IEs	OPTIONAL
}

RRCConnectionReconfigurationComplete-v1250-IEs ::= SEQUENCE {
	logMeasAvailableMBSFN-r12			ENUMERATED {true}				OPTIONAL,
	nonCriticalExtension				SEQUENCE {}						OPTIONAL
}

-- ASN1STOP

-	RRCConnectionReestablishment
The RRCConnectionReestablishment message is used to re-establish SRB1.
Signalling radio bearer: SRB0
RLC-SAP: TM
Logical channel: CCCH
Direction: E-UTRAN to UE
RRCConnectionReestablishment message
-- ASN1START

RRCConnectionReestablishment ::=	SEQUENCE {
	rrc-TransactionIdentifier			RRC-TransactionIdentifier,
	criticalExtensions					CHOICE {
		c1									CHOICE{
			rrcConnectionReestablishment-r8		RRCConnectionReestablishment-r8-IEs,
			spare7 NULL,
			spare6 NULL, spare5 NULL, spare4 	NULL,
			spare3 NULL, spare2 NULL, spare1 	NULL
		},
		criticalExtensionsFuture			SEQUENCE {}
	}
}

RRCConnectionReestablishment-r8-IEs ::= SEQUENCE {
	radioResourceConfigDedicated		RadioResourceConfigDedicated,
	nextHopChainingCount				NextHopChainingCount,
	nonCriticalExtension				RRCConnectionReestablishment-v8a0-IEs	OPTIONAL
}

RRCConnectionReestablishment-v8a0-IEs ::= SEQUENCE {
	lateNonCriticalExtension			OCTET STRING						OPTIONAL,
	nonCriticalExtension				SEQUENCE {}							OPTIONAL
}

-- ASN1STOP

-	RRCConnectionReestablishmentComplete
The RRCConnectionReestablishmentComplete message is used to confirm the successful completion of an RRC connection reestablishment.
Signalling radio bearer: SRB1
RLC-SAP: AM
Logical channel: DCCH
Direction: UE to E-UTRAN
RRCConnectionReestablishmentComplete message
-- ASN1START

RRCConnectionReestablishmentComplete ::= SEQUENCE {
	rrc-TransactionIdentifier			RRC-TransactionIdentifier,
	criticalExtensions					CHOICE {
		rrcConnectionReestablishmentComplete-r8
											RRCConnectionReestablishmentComplete-r8-IEs,
		criticalExtensionsFuture			SEQUENCE {}
	}
}

RRCConnectionReestablishmentComplete-r8-IEs ::= SEQUENCE {
	nonCriticalExtension				RRCConnectionReestablishmentComplete-v920-IEs	OPTIONAL
}

RRCConnectionReestablishmentComplete-v920-IEs ::= SEQUENCE {
	rlf-InfoAvailable-r9				ENUMERATED {true}				OPTIONAL,
	nonCriticalExtension				RRCConnectionReestablishmentComplete-v8a0-IEs	OPTIONAL
}

RRCConnectionReestablishmentComplete-v8a0-IEs ::= SEQUENCE {
	lateNonCriticalExtension			OCTET STRING						OPTIONAL,
	nonCriticalExtension				RRCConnectionReestablishmentComplete-v1020-IEs	OPTIONAL
}

RRCConnectionReestablishmentComplete-v1020-IEs ::= SEQUENCE {
	logMeasAvailable-r10				ENUMERATED {true}				OPTIONAL,
	nonCriticalExtension				RRCConnectionReestablishmentComplete-v1130-IEs	OPTIONAL
}

RRCConnectionReestablishmentComplete-v1130-IEs ::= SEQUENCE {
	connEstFailInfoAvailable-r11		ENUMERATED {true}				OPTIONAL,
	nonCriticalExtension				RRCConnectionReestablishmentComplete-v1250-IEs	OPTIONAL
}

RRCConnectionReestablishmentComplete-v1250-IEs ::= SEQUENCE {
	logMeasAvailableMBSFN-r12			ENUMERATED {true}				OPTIONAL,
	nonCriticalExtension				SEQUENCE {}						OPTIONAL
}

-- ASN1STOP

RRCConnectionReestablishmentComplete field descriptions
rlf-InfoAvailable
This field is used to indicate the availability of radio link failure or handover failure related measurements

-	RRCConnectionReestablishmentReject
The RRCConnectionReestablishmentReject message is used to indicate the rejection of an RRC connection reestablishment request.
Signalling radio bearer: SRB0
RLC-SAP: TM
Logical channel: CCCH
Direction: E-UTRAN to UE
RRCConnectionReestablishmentReject message
-- ASN1START

RRCConnectionReestablishmentReject ::= SEQUENCE {
	criticalExtensions					CHOICE {
		rrcConnectionReestablishmentReject-r8
											RRCConnectionReestablishmentReject-r8-IEs,
		criticalExtensionsFuture			SEQUENCE {}
	}
}

RRCConnectionReestablishmentReject-r8-IEs ::= SEQUENCE {
	nonCriticalExtension				RRCConnectionReestablishmentReject-v8a0-IEs	OPTIONAL
}

RRCConnectionReestablishmentReject-v8a0-IEs ::= SEQUENCE {
	lateNonCriticalExtension			OCTET STRING						OPTIONAL,
	nonCriticalExtension				SEQUENCE {}							OPTIONAL
}

-- ASN1STOP

-	RRCConnectionReestablishmentRequest
The RRCConnectionReestablishmentRequest message is used to request the reestablishment of an RRC connection.
Signalling radio bearer: SRB0
RLC-SAP: TM
Logical channel: CCCH
Direction: UE to E-UTRAN
RRCConnectionReestablishmentRequest message
-- ASN1START

RRCConnectionReestablishmentRequest ::= SEQUENCE {
	criticalExtensions					CHOICE {
		rrcConnectionReestablishmentRequest-r8
											RRCConnectionReestablishmentRequest-r8-IEs,
		criticalExtensionsFuture			SEQUENCE {}
	}
}

RRCConnectionReestablishmentRequest-r8-IEs ::= SEQUENCE {
	ue-Identity							ReestabUE-Identity,
	reestablishmentCause				ReestablishmentCause,
	spare								BIT STRING (SIZE (2))
}

ReestabUE-Identity ::=				SEQUENCE {
	c-RNTI								C-RNTI,
	physCellId							PhysCellId,
	shortMAC-I							ShortMAC-I
}

ReestablishmentCause ::=			ENUMERATED {
										reconfigurationFailure, handoverFailure,
										otherFailure, spare1}

-- ASN1STOP

RRCConnectionReestablishmentRequest field descriptions
physCellId
The Physical Cell Identity of the PCell the UE was connected to prior to the failure.
reestablishmentCause
Indicates the failure cause that triggered the re-establishment procedure.
ue-Identity
UE identity included to retrieve UE context and to facilitate contention resolution by lower layers.

-	RRCConnectionReject
The RRCConnectionReject message is used to reject the RRC connection establishment.
Signalling radio bearer: SRB0
RLC-SAP: TM
Logical channel: CCCH
Direction: E-UTRAN to UE
RRCConnectionReject message
-- ASN1START

RRCConnectionReject ::=				SEQUENCE {
	criticalExtensions					CHOICE {
		c1									CHOICE {
			rrcConnectionReject-r8				RRCConnectionReject-r8-IEs,
			spare3 NULL, spare2 NULL, spare1 NULL
		},
		criticalExtensionsFuture			SEQUENCE {}
	}
}

RRCConnectionReject-r8-IEs ::=		SEQUENCE {
	waitTime							INTEGER (1..16),
	nonCriticalExtension				RRCConnectionReject-v8a0-IEs		OPTIONAL
}

RRCConnectionReject-v8a0-IEs ::= SEQUENCE {
	lateNonCriticalExtension			OCTET STRING						OPTIONAL,
	nonCriticalExtension				RRCConnectionReject-v1020-IEs		OPTIONAL
}

RRCConnectionReject-v1020-IEs ::=	SEQUENCE {
	extendedWaitTime-r10				INTEGER (1..1800)					OPTIONAL,	-- Need ON
	nonCriticalExtension				RRCConnectionReject-v1130-IEs		OPTIONAL
}

RRCConnectionReject-v1130-IEs ::=	SEQUENCE {
	deprioritisationReq-r11				SEQUENCE {
		deprioritisationType-r11			ENUMERATED {frequency, e-utra},
		deprioritisationTimer-r11			ENUMERATED {min5, min10, min15, min30}
	}																		OPTIONAL,	-- Need ON
	nonCriticalExtension				SEQUENCE {}							OPTIONAL
}

-- ASN1STOP

RRCConnectionReject field descriptions
deprioritisationReq
Indicates whether the current frequency or RAT is to be de-prioritised. The UE shall be able to store a depriotisation request for up to 8 frequencies (applicable when receiving another frequency specific deprioritisation request before T325 expiry).
deprioritisationTimer
Indicates the period for which either the current carrier frequency or E-UTRA is deprioritised. Value minN corresponds to N minutes.
extendedWaitTime
Value in seconds for the wait time for Delay Tolerant access requests.
waitTime
Wait time value in seconds.

-	RRCConnectionRelease
The RRCConnectionRelease message is used to command the release of an RRC connection.
Signalling radio bearer: SRB1
RLC-SAP: AM
Logical channel: DCCH
Direction: E-UTRAN to UE
RRCConnectionRelease message
-- ASN1START

RRCConnectionRelease ::=			SEQUENCE {
	rrc-TransactionIdentifier			RRC-TransactionIdentifier,
	criticalExtensions					CHOICE {
		c1									CHOICE {
			rrcConnectionRelease-r8				RRCConnectionRelease-r8-IEs,
			spare3 NULL, spare2 NULL, spare1 NULL
		},
		criticalExtensionsFuture			SEQUENCE {}
	}
}

RRCConnectionRelease-r8-IEs ::=		SEQUENCE {
	releaseCause						ReleaseCause,
	redirectedCarrierInfo				RedirectedCarrierInfo				OPTIONAL,	-- Need ON
	idleModeMobilityControlInfo			IdleModeMobilityControlInfo			OPTIONAL,	-- Need OP
	nonCriticalExtension				RRCConnectionRelease-v890-IEs		OPTIONAL
}

RRCConnectionRelease-v890-IEs ::=	SEQUENCE {
	lateNonCriticalExtension			OCTET STRING (CONTAINING RRCConnectionRelease-v9e0-IEs)	OPTIONAL,
	nonCriticalExtension				RRCConnectionRelease-v920-IEs		OPTIONAL
}

-- Late non critical extensions
RRCConnectionRelease-v9e0-IEs ::= SEQUENCE {
	redirectedCarrierInfo-v9e0			RedirectedCarrierInfo-v9e0			OPTIONAL,	-- Cond NoRedirect-r8
	idleModeMobilityControlInfo-v9e0	IdleModeMobilityControlInfo-v9e0	OPTIONAL,	-- Cond IdleInfoEUTRA
	nonCriticalExtension				SEQUENCE {}							OPTIONAL
}

-- Regular non critical extensions
RRCConnectionRelease-v920-IEs ::=	SEQUENCE {
	cellInfoList-r9					CHOICE {
		geran-r9						CellInfoListGERAN-r9,
		utra-FDD-r9						CellInfoListUTRA-FDD-r9,
		utra-TDD-r9						CellInfoListUTRA-TDD-r9,
		...,
		utra-TDD-r10					CellInfoListUTRA-TDD-r10
	}															OPTIONAL,	-- Cond Redirection
	nonCriticalExtension			RRCConnectionRelease-v1020-IEs		OPTIONAL
}

RRCConnectionRelease-v1020-IEs ::=	SEQUENCE {
	extendedWaitTime-r10				INTEGER (1..1800)		OPTIONAL,	-- Need ON
	nonCriticalExtension			SEQUENCE {}				OPTIONAL
}

ReleaseCause ::=				ENUMERATED {loadBalancingTAUrequired,
											other, cs-FallbackHighPriority-v1020, spare1}

RedirectedCarrierInfo ::=			CHOICE {
	eutra								ARFCN-ValueEUTRA,
	geran								CarrierFreqsGERAN,
	utra-FDD							ARFCN-ValueUTRA,
	utra-TDD							ARFCN-ValueUTRA,
	cdma2000-HRPD						CarrierFreqCDMA2000,
	cdma2000-1xRTT						CarrierFreqCDMA2000,
	...,
	utra-TDD-r10						CarrierFreqListUTRA-TDD-r10
}

RedirectedCarrierInfo-v9e0 ::=			SEQUENCE {
	eutra-v9e0								ARFCN-ValueEUTRA-v9e0
}

CarrierFreqListUTRA-TDD-r10 ::=			SEQUENCE (SIZE (1..maxFreqUTRA-TDD-r10)) OF ARFCN-ValueUTRA

IdleModeMobilityControlInfo ::=		SEQUENCE {
	freqPriorityListEUTRA				FreqPriorityListEUTRA			OPTIONAL,		-- Need ON
	freqPriorityListGERAN				FreqsPriorityListGERAN			OPTIONAL,		-- Need ON
	freqPriorityListUTRA-FDD			FreqPriorityListUTRA-FDD		OPTIONAL,		-- Need ON
	freqPriorityListUTRA-TDD			FreqPriorityListUTRA-TDD		OPTIONAL,		-- Need ON
	bandClassPriorityListHRPD			BandClassPriorityListHRPD		OPTIONAL,		-- Need ON
	bandClassPriorityList1XRTT			BandClassPriorityList1XRTT		OPTIONAL,		-- Need ON
	t320								ENUMERATED {
											min5, min10, min20, min30, min60, min120, min180,
											spare1}						OPTIONAL,		-- Need OR
	...,
	[[	freqPriorityListExtEUTRA-r12		FreqPriorityListExtEUTRA-r12		OPTIONAL		-- Need ON
	]],
	[[	freqPriorityListEUTRA-v13xy			FreqPriorityListEUTRA-v13xy			OPTIONAL,		-- Need ON
		freqPriorityListExtEUTRA-v13xy		FreqPriorityListExtEUTRA-v13xy		OPTIONAL		-- Need ON
	]]
}

IdleModeMobilityControlInfo-v9e0 ::=	SEQUENCE {
	freqPriorityListEUTRA-v9e0			SEQUENCE (SIZE (1..maxFreq)) OF FreqPriorityEUTRA-v9e0
}

FreqPriorityListEUTRA ::=			SEQUENCE (SIZE (1..maxFreq)) OF FreqPriorityEUTRA

FreqPriorityListExtEUTRA-r12 ::=		SEQUENCE (SIZE (1..maxFreq)) OF FreqPriorityEUTRA-r12

FreqPriorityListEUTRA-v13xy ::=			SEQUENCE (SIZE (1..maxFreq)) OF FreqPriorityEUTRA-v13xy

FreqPriorityListExtEUTRA-v13xy ::=		SEQUENCE (SIZE (1..maxFreq)) OF FreqPriorityEUTRA-v13xy

FreqPriorityEUTRA ::=				SEQUENCE {
	carrierFreq							ARFCN-ValueEUTRA,
	cellReselectionPriority				CellReselectionPriority
}

FreqPriorityEUTRA-v9e0 ::=			SEQUENCE {
	carrierFreq-v9e0					ARFCN-ValueEUTRA-v9e0		OPTIONAL	-- Cond EARFCN-max
}

FreqPriorityEUTRA-r12 ::=				SEQUENCE {
	carrierFreq-r12							ARFCN-ValueEUTRA-r9,
	cellReselectionPriority-r12				CellReselectionPriority
}

FreqPriorityEUTRA-v13xy ::=				SEQUENCE {
	cellReselectionSubPriority-r13				CellReselectionSubPriority-r13 		OPTIONAL		-- Need ON
}

FreqsPriorityListGERAN ::=			SEQUENCE (SIZE (1..maxGNFG)) OF FreqsPriorityGERAN

FreqsPriorityGERAN ::=				SEQUENCE {
	carrierFreqs						CarrierFreqsGERAN,
	cellReselectionPriority				CellReselectionPriority
}

FreqPriorityListUTRA-FDD ::=		SEQUENCE (SIZE (1..maxUTRA-FDD-Carrier)) OF FreqPriorityUTRA-FDD

FreqPriorityUTRA-FDD ::=			SEQUENCE {
	carrierFreq							ARFCN-ValueUTRA,
	cellReselectionPriority				CellReselectionPriority
}

FreqPriorityListUTRA-TDD ::=		SEQUENCE (SIZE (1..maxUTRA-TDD-Carrier)) OF FreqPriorityUTRA-TDD

FreqPriorityUTRA-TDD ::=			SEQUENCE {
	carrierFreq							ARFCN-ValueUTRA,
	cellReselectionPriority				CellReselectionPriority
}

BandClassPriorityListHRPD ::=		SEQUENCE (SIZE (1..maxCDMA-BandClass)) OF BandClassPriorityHRPD

BandClassPriorityHRPD ::=			SEQUENCE {
	bandClass							BandclassCDMA2000,
	cellReselectionPriority				CellReselectionPriority
}

BandClassPriorityList1XRTT ::=	SEQUENCE (SIZE (1..maxCDMA-BandClass)) OF BandClassPriority1XRTT

BandClassPriority1XRTT ::=			SEQUENCE {
	bandClass							BandclassCDMA2000,
	cellReselectionPriority				CellReselectionPriority
}

CellInfoListGERAN-r9 ::=		SEQUENCE (SIZE (1..maxCellInfoGERAN-r9)) OF CellInfoGERAN-r9

CellInfoGERAN-r9 ::=				SEQUENCE {
	physCellId-r9						PhysCellIdGERAN,
	carrierFreq-r9						CarrierFreqGERAN,
	systemInformation-r9				SystemInfoListGERAN
}

CellInfoListUTRA-FDD-r9 ::=			SEQUENCE (SIZE (1..maxCellInfoUTRA-r9)) OF CellInfoUTRA-FDD-r9

CellInfoUTRA-FDD-r9 ::=				SEQUENCE {
	physCellId-r9						PhysCellIdUTRA-FDD,
	utra-BCCH-Container-r9				OCTET STRING
}

CellInfoListUTRA-TDD-r9 ::=			SEQUENCE (SIZE (1..maxCellInfoUTRA-r9)) OF CellInfoUTRA-TDD-r9

CellInfoUTRA-TDD-r9 ::=				SEQUENCE {
	physCellId-r9						PhysCellIdUTRA-TDD,
	utra-BCCH-Container-r9				OCTET STRING
}

CellInfoListUTRA-TDD-r10 ::=		SEQUENCE (SIZE (1..maxCellInfoUTRA-r9)) OF CellInfoUTRA-TDD-r10

CellInfoUTRA-TDD-r10 ::=			SEQUENCE {
	physCellId-r10						PhysCellIdUTRA-TDD,
	carrierFreq-r10						ARFCN-ValueUTRA,
	utra-BCCH-Container-r10				OCTET STRING
}

-- ASN1STOP

RRCConnectionRelease field descriptions
carrierFreq or bandClass
The carrier frequency (UTRA and E-UTRA) and band class (HRPD and 1xRTT) for which the associated cellReselectionPriority is applied.
carrierFreqs
The list of GERAN carrier frequencies organised into one group of GERAN carrier frequencies.
cellInfoList
Used to provide system information of one or more cells on the redirected inter-RAT carrier frequency. The system information can be used if, upon redirection, the UE selects an inter-RAT cell indicated by the physCellId and carrierFreq (GERAN and UTRA TDD) or by the physCellId (other RATs). The choice shall match the redirectedCarrierInfo. In particular, E-UTRAN only applies value utra-TDD-r10 in case redirectedCarrierInfo is set to utra-TDD-r10.
cellReselectionSubPriority
Fractional priority value added to cellReselectionPriority for the carrier.
extendedWaitTime
Value in seconds for the wait time for Delay Tolerant access requests.
freqPriorityListX
Provides a cell reselection priority for each frequency, by means of separate lists for each RAT (including E-UTRA). The UE shall be able to store at least 3 occurrences of FreqsPriorityGERAN. If E-UTRAN includes freqPriorityListEUTRA-v9e0 it includes the same number of entries, and listed in the same order, as in freqPriorityListEUTRA (i.e. without suffix). Field freqPriorityListExt includes additional neighbouring inter-frequencies, i.e. extending the size of the inter-frequency carrier list using the general principles specified in 5.1.2. EUTRAN only includes freqPriorityListExtEUTRA if freqPriorityListEUTRA (i.e without suffix) includes maxFreq entries.
idleModeMobilityControlInfo
Provides dedicated cell reselection priorities. Used for cell reselection as specified in TS 36.304 [4]. For E-UTRA and UTRA frequencies, a UE that supports multi-band cells for the concerned RAT considers the dedicated priorities to be common for all overlapping bands (i.e. regardless of the ARFCN that is used).
redirectedCarrierInfo
The redirectedCarrierInfo indicates a carrier frequency (downlink for FDD) and is used to redirect the UE to an E-UTRA or an inter-RAT carrier frequency, by means of the cell selection upon leaving RRC_CONNECTED as specified in TS 36.304 [4].
releaseCause
The releaseCause is used to indicate the reason for releasing the RRC Connection. The cause value cs-FallbackHighPriority is only applicable when redirectedCarrierInfo is present with the value set to utra-FDD, utra-TDD or utra-TDD-r10.
E-UTRAN should not set the releaseCause to loadBalancingTAURequired or to cs-FallbackHighPriority if the extendedWaitTime is present.
systemInformation
Container for system information of the GERAN cell i.e. one or more System Information (SI) messages as defined in TS 44.018 [45, table 9.1.1]. 
t320
Timer T320 as described in section 7.3. Value minN corresponds to N minutes.
utra-BCCH-Container
Contains System Information Container message as defined in TS 25.331 [19].

Conditional presence
Explanation
EARFCN-max
The field is mandatory present if the corresponding carrierFreq (i.e. without suffix) is set to maxEARFCN. Otherwise the field is not present.
IdleInfoEUTRA
The field is optionally present, need OP, if the IdleModeMobilityControlInfo (i.e. without suffix) is included and includes freqPriorityListEUTRA; otherwise the field is not present.
NoRedirect-r8
The field is optionally present, need OP, if the redirectedCarrierInfo (i.e. without suffix) is not included; otherwise the field is not present.
Redirection
The field is optionally present, need ON, if the redirectedCarrierInfo is included and set to geran, utra-FDD, utra-TDD or utra-TDD-r10; otherwise the field is not present.

-	RRCConnectionRequest
The RRCConnectionRequest message is used to request the establishment of an RRC connection.
Signalling radio bearer: SRB0
RLC-SAP: TM
Logical channel: CCCH
Direction: UE to E-UTRAN
RRCConnectionRequest message
-- ASN1START

RRCConnectionRequest ::=			SEQUENCE {
	criticalExtensions					CHOICE {
		rrcConnectionRequest-r8				RRCConnectionRequest-r8-IEs,
		criticalExtensionsFuture			SEQUENCE {}
	}
}

RRCConnectionRequest-r8-IEs ::=		SEQUENCE {
	ue-Identity							InitialUE-Identity,
	establishmentCause					EstablishmentCause,
	spare								BIT STRING (SIZE (1))
}

InitialUE-Identity ::=				CHOICE {
	s-TMSI								S-TMSI,
	randomValue							BIT STRING (SIZE (40))
}

EstablishmentCause ::=				ENUMERATED {
										emergency, highPriorityAccess, mt-Access, mo-Signalling,
										mo-Data, delayTolerantAccess-v1020, mo-VoiceCall-v1280, spare1}

-- ASN1STOP

RRCConnectionRequest field descriptions
establishmentCause
Provides the establishment cause for the RRC connection request as provided by the upper layers. W.r.t. the cause value names: highPriorityAccess concerns AC11..AC15, 'mt' stands for 'Mobile Terminating' and 'mo' for 'Mobile Originating.
randomValue
Integer value in the range 0 to 240 ? 1.
ue-Identity
UE identity included to facilitate contention resolution by lower layers.

-	RRCConnectionSetup
The RRCConnectionSetup message is used to establish SRB1.
Signalling radio bearer: SRB0
RLC-SAP: TM
Logical channel: CCCH
Direction: E-UTRAN to UE
RRCConnectionSetup message
-- ASN1START

RRCConnectionSetup ::=				SEQUENCE {
	rrc-TransactionIdentifier			RRC-TransactionIdentifier,
	criticalExtensions					CHOICE {
		c1									CHOICE {
			rrcConnectionSetup-r8				RRCConnectionSetup-r8-IEs,
			spare7 NULL,
			spare6 NULL, spare5 NULL, spare4 NULL,
			spare3 NULL, spare2 NULL, spare1 NULL
		},
		criticalExtensionsFuture			SEQUENCE {}
	}
}

RRCConnectionSetup-r8-IEs ::=		SEQUENCE {
	radioResourceConfigDedicated		RadioResourceConfigDedicated,
	nonCriticalExtension				RRCConnectionSetup-v8a0-IEs			OPTIONAL
}

RRCConnectionSetup-v8a0-IEs ::= SEQUENCE {
	lateNonCriticalExtension			OCTET STRING						OPTIONAL,
	nonCriticalExtension				SEQUENCE {}							OPTIONAL
}

-- ASN1STOP

-	RRCConnectionSetupComplete
The RRCConnectionSetupComplete message is used to confirm the successful completion of an RRC connection establishment.
Signalling radio bearer: SRB1
RLC-SAP: AM
Logical channel: DCCH
Direction: UE to E-UTRAN
RRCConnectionSetupComplete message
-- ASN1START

RRCConnectionSetupComplete ::=		SEQUENCE {
	rrc-TransactionIdentifier			RRC-TransactionIdentifier,
	criticalExtensions					CHOICE {
		c1									CHOICE{
			rrcConnectionSetupComplete-r8		RRCConnectionSetupComplete-r8-IEs,
			spare3 NULL, spare2 NULL, spare1 NULL
		},
		criticalExtensionsFuture			SEQUENCE {}
	}
}

RRCConnectionSetupComplete-r8-IEs ::= SEQUENCE {
	selectedPLMN-Identity				INTEGER (1..maxPLMN-r11),
	registeredMME						RegisteredMME						OPTIONAL,
	dedicatedInfoNAS					DedicatedInfoNAS,
	nonCriticalExtension				RRCConnectionSetupComplete-v8a0-IEs	OPTIONAL
}

RRCConnectionSetupComplete-v8a0-IEs ::= SEQUENCE {
	lateNonCriticalExtension			OCTET STRING						OPTIONAL,
	nonCriticalExtension				RRCConnectionSetupComplete-v1020-IEs	OPTIONAL
}

RRCConnectionSetupComplete-v1020-IEs ::= SEQUENCE {
	gummei-Type-r10						ENUMERATED {native, mapped}			OPTIONAL,
	rlf-InfoAvailable-r10				ENUMERATED {true}					OPTIONAL,
	logMeasAvailable-r10				ENUMERATED {true}					OPTIONAL,
	rn-SubframeConfigReq-r10			ENUMERATED {required, notRequired}	OPTIONAL,
	nonCriticalExtension				RRCConnectionSetupComplete-v1130-IEs	OPTIONAL
}

RRCConnectionSetupComplete-v1130-IEs ::= SEQUENCE {
	connEstFailInfoAvailable-r11		ENUMERATED {true}				OPTIONAL,
	nonCriticalExtension				RRCConnectionSetupComplete-v1250-IEs		OPTIONAL
}

RRCConnectionSetupComplete-v1250-IEs ::= SEQUENCE {
	mobilityState-r12					ENUMERATED {normal, medium, high, spare}	OPTIONAL,
	mobilityHistoryAvail-r12			ENUMERATED {true}				OPTIONAL,
	logMeasAvailableMBSFN-r12			ENUMERATED {true}				OPTIONAL,
	nonCriticalExtension				SEQUENCE {}						OPTIONAL
}

RegisteredMME ::=					SEQUENCE {
	plmn-Identity						PLMN-Identity						OPTIONAL,
	mmegi								BIT STRING (SIZE (16)),
	mmec								MMEC
}

-- ASN1STOP

RRCConnectionSetupComplete field descriptions
gummei-Type
This field is used to indicate whether the GUMMEI included is native (assigned by EPC) or mapped (from 2G/3G identifiers).
mmegi
Provides the Group Identity of the registered MME within the PLMN, as provided by upper layers, see TS 23.003 [27].
mobilityState
This field indicates the UE mobility state (as defined in TS 36.304 [4, 5.2.4.3]) just prior to UE going into RRC_CONNECTED state. The UE indicates the value of medium and high when being in Medium-mobility and High-mobility states respectively. Otherwise the UE indicates the value normal.
registeredMME
This field is used to transfer the GUMMEI of the MME where the UE is registered, as provided by upper layers.
rn-SubframeConfigReq
If present, this field indicates that the connection establishment is for an RN and whether a subframe configuration is requested or not.
selectedPLMN-Identity
Index of the PLMN selected by the UE from the plmn-IdentityList included in SIB1. 1 if the 1st PLMN is selected from the plmn-IdentityList included in SIB1, 2 if the 2nd PLMN is selected from the plmn-IdentityList included in SIB1 and so on.

-	SCGFailureInformation
The SCGFailureInformation message is used to provide information regarding failures detected by the UE.
Signalling radio bearer: SRB1
RLC-SAP: AM
Logical channel: DCCH
Direction: UE to E-UTRAN
SCGFailureInformation message
-- ASN1START

SCGFailureInformation-r12 ::=		SEQUENCE {
	criticalExtensions					CHOICE {
		c1									CHOICE {
			scgFailureInformation-r12			SCGFailureInformation-r12-IEs,
			spare3 NULL, spare2 NULL, spare1 NULL
		},
		criticalExtensionsFuture			SEQUENCE {}
	}
}

SCGFailureInformation-r12-IEs ::=	SEQUENCE {
	failureReportSCG-r12				FailureReportSCG-r12 			OPTIONAL,
	nonCriticalExtension				SEQUENCE {}							OPTIONAL
}

FailureReportSCG-r12 ::= 			SEQUENCE {
	failureType-r12						ENUMERATED {t313-Expiry, randomAccessProblem,
												rlc-MaxNumRetx, scg-ChangeFailure },
	measResultServFreqList-r12			MeasResultServFreqList-r10		OPTIONAL,
	measResultNeighCells-r12			MeasResultList2EUTRA-r9			OPTIONAL,
	...,
	[[
	measResultServFreqListExt-r13			MeasResultServFreqListExt-r13		OPTIONAL
	]]
}

-- ASN1STOP

-	SCPTMConfiguration
The SCPTMConfiguration message contains the control information applicable for MBMS services transmitted via SC-MRB.
Signalling radio bearer: N/A
RLC-SAP: UM
Logical channel: SC-MCCH
Direction: E-UTRAN to UE
SCPTMConfiguration message
-- ASN1START

SCPTMConfiguration-r13 ::=		SEQUENCE {
	sc-mtch-InfoList-r13			SC-MTCH-InfoList-r13,
	scptmNeighbourCellList-r13		SCPTMNeighbourCellList-r13			OPTIONAL,
	...
}

-- ASN1STOP

SCPTMConfiguration field descriptions
sc-mtch-InfoList
Provides the configuration of each SC-MTCH in the current cell.
scptmNeighbourCellList
List of neighbour cells providing MBMS services via SC-MRB. Absence of this field means that MBMS services listed in the SCPTMConfiguration message are not provided via SC-MRB in any neighbour cell.

-	SecurityModeCommand
The SecurityModeCommand message is used to command the activation of AS security.
Signalling radio bearer: SRB1
RLC-SAP: AM
Logical channel: DCCH
Direction: E-UTRAN to UE
SecurityModeCommand message
-- ASN1START

SecurityModeCommand ::=				SEQUENCE {
	rrc-TransactionIdentifier			RRC-TransactionIdentifier,
	criticalExtensions					CHOICE {
		c1									CHOICE{
			securityModeCommand-r8				SecurityModeCommand-r8-IEs,
			spare3 NULL, spare2 NULL, spare1 NULL
		},
		criticalExtensionsFuture			SEQUENCE {}
	}
}

SecurityModeCommand-r8-IEs ::=		SEQUENCE {
	securityConfigSMC					SecurityConfigSMC,
	nonCriticalExtension				SecurityModeCommand-v8a0-IEs		OPTIONAL
}

SecurityModeCommand-v8a0-IEs ::= SEQUENCE {
	lateNonCriticalExtension			OCTET STRING						OPTIONAL,
	nonCriticalExtension				SEQUENCE {}							OPTIONAL
}

SecurityConfigSMC ::=					SEQUENCE {
	securityAlgorithmConfig					SecurityAlgorithmConfig,
	...
}

-- ASN1STOP

-	SecurityModeComplete
The SecurityModeComplete message is used to confirm the successful completion of a security mode command.
Signalling radio bearer: SRB1
RLC-SAP: AM
Logical channel: DCCH
Direction: UE to E-UTRAN
SecurityModeComplete message
-- ASN1START

SecurityModeComplete ::=			SEQUENCE {
	rrc-TransactionIdentifier			RRC-TransactionIdentifier,
	criticalExtensions					CHOICE {
		securityModeComplete-r8				SecurityModeComplete-r8-IEs,
		criticalExtensionsFuture			SEQUENCE {}
	}
}

SecurityModeComplete-r8-IEs ::=		SEQUENCE {
	nonCriticalExtension				SecurityModeComplete-v8a0-IEs							OPTIONAL
}

SecurityModeComplete-v8a0-IEs ::= SEQUENCE {
	lateNonCriticalExtension			OCTET STRING						OPTIONAL,
	nonCriticalExtension				SEQUENCE {}							OPTIONAL
}

-- ASN1STOP

-	SecurityModeFailure
The SecurityModeFailure message is used to indicate an unsuccessful completion of a security mode command.
Signalling radio bearer: SRB1
RLC-SAP: AM
Logical channel: DCCH
Direction: UE to E-UTRAN
SecurityModeFailure message
-- ASN1START

SecurityModeFailure ::=				SEQUENCE {
	rrc-TransactionIdentifier			RRC-TransactionIdentifier,
	criticalExtensions					CHOICE {
		securityModeFailure-r8				SecurityModeFailure-r8-IEs,
		criticalExtensionsFuture			SEQUENCE {}
	}
}

SecurityModeFailure-r8-IEs ::=		SEQUENCE {
	nonCriticalExtension				SecurityModeFailure-v8a0-IEs							OPTIONAL
}

SecurityModeFailure-v8a0-IEs ::= SEQUENCE {
	lateNonCriticalExtension			OCTET STRING						OPTIONAL,
	nonCriticalExtension				SEQUENCE {}							OPTIONAL
}

-- ASN1STOP

-	SidelinkUEInformation
The SidelinkUEInformation message is used for the indication of sidelink information to the eNB.
Signalling radio bearer: SRB1
RLC-SAP: AM
Logical channel: DCCH
Direction: UE to E-UTRAN
SidelinkUEInformation message
-- ASN1START

SidelinkUEInformation-r12 ::=		SEQUENCE {
	criticalExtensions				CHOICE {
		c1								CHOICE {
			sidelinkUEInformation-r12		SidelinkUEInformation-r12-IEs,
			spare3 NULL, spare2 NULL, spare1 NULL
		},
		criticalExtensionsFuture			SEQUENCE {}
	}
}

SidelinkUEInformation-r12-IEs ::=	SEQUENCE {
	commRxInterestedFreq-r12		ARFCN-ValueEUTRA-r9			OPTIONAL,
	commTxResourceReq-r12			SL-CommTxResourceReq-r12	OPTIONAL,
	discRxInterest-r12				ENUMERATED {true}			OPTIONAL,
	discTxResourceReq-r12			INTEGER (1..63)				OPTIONAL,
	lateNonCriticalExtension		OCTET STRING				OPTIONAL,
	nonCriticalExtension			SidelinkUEInformation-v13x0-IEs	OPTIONAL
}

SidelinkUEInformation-v13x0-IEs ::=	SEQUENCE {
	commTxResourceReq121-r13		SL-CommTxResourceReqUC-r13	OPTIONAL,
	commTxResourceInfoReqRelay-r13		SEQUENCE {
		commTxResourceReqRelay-r13		SL-CommTxResourceReqUC-r13,
		ue-Type-r13						ENUMERATED {relayUE, remoteUE}
	}															OPTIONAL,
	discTxResourceReq-v13x0			SEQUENCE {
		carrierFreqDiscTx-r13			INTEGER (1..maxFreq),
		discTxResourceReqAddFreq-r13	SL-DiscTxResourceReqPerFreqList-r13	OPTIONAL
	}															OPTIONAL,
	discTxResourceReqPS-r13			SL-DiscTxResourceReq-r13	OPTIONAL,
	discRxGapReq-r13					SL-GapRequest-r13			OPTIONAL,
	discTxGapReq-r13					SL-GapRequest-r13			OPTIONAL,
	discSysInfoReportList-r13			SL-SysInfoReportList-r13	OPTIONAL,
	nonCriticalExtension			SEQUENCE {}					OPTIONAL
}

SL-CommTxResourceReq-r12 ::=		SEQUENCE {
	carrierFreq-r12					ARFCN-ValueEUTRA-r9			OPTIONAL,
	destinationInfoList-r12			SL-DestinationInfoList-r12
}

SL-CommTxResourceReqUC-r13 ::=		SEQUENCE {
	carrierFreq-r13					ARFCN-ValueEUTRA-r9			OPTIONAL,
	destinationInfoListUC-r13			SL-DestinationInfoListUC-r13
}

SL-DiscTxResourceReqPerFreqList-r13 ::=	SEQUENCE (SIZE (1..maxFreq)) OF SL-DiscTxResourceReq-r13

SL-DiscTxResourceReq-r13 ::=		SEQUENCE {
	carrierFreq-r13					ARFCN-ValueEUTRA-r9			OPTIONAL,
	discTxResourceReq-r13			INTEGER (1..63)
}

SL-DestinationInfoList-r12 ::=	SEQUENCE (SIZE (1..maxSL-Dest-r12)) OF SL-DestinationIdentity-r12

SL-DestinationIdentity-r12 ::=	BIT STRING (SIZE (24))

SL-DestinationInfoListUC-r13 ::=	SL-DestinationInfoList-r12

SL-SysInfoReportList-r13 ::=	SEQUENCE (SIZE (1.. maxSL-DiscSysInfoReportFreq-r13)) OF SL-SysInfoReport-r13

-- ASN1STOP

SidelinkUEInformation field descriptions
carrierFreqDiscTx
Indicates the frequency by the index of the entry in field discInterFreqList within SystemInformationBlockType19. Value 0 corresponds to the first entry in discInterFreqList within SystemInformationBlockType19, value 1 corresponds to the second entry in this list and so on.
commRxInterestedFreq
Indicates the frequency on which the UE is interested to receive sidelink communication.
commTxResourceReq
Indicates the frequency on which the UE is interested to transmit sidelink communication as well as the sidelink communication transmission destination(s) for which the UE requests E-UTRAN to assign dedicated resources.
commTxResourceReq121
Indicates the frequency on which the UE is interested to transmit non-relay related sidelink one to one communication as well as the sidelink communication transmission destination(s) for which the UE requests E-UTRAN to assign dedicated resources.
commTxResourceReqRelay
Indicates the relay related sidelink communication transmission destination(s) for which the relay or remote UE requests E-UTRAN to assign dedicated resources i.e. either contains relay or remote UE's unicast destination identity.
destinationInfoList
Indicates the destination which is identified by the ProSe Layer-2 Group ID as specified in TS 23.303 [68].
destinationInfoListUC
Indicates the unicast destination, as specified in TS 23.303 [68].
discRxInterest
Indicates that the UE is interested to monitor sidelink discovery announcements.
discTxResourceReq
Indicates the number of separate discovery message(s) the UE wants to transmit every discovery period. This field concerns the resources the UE requires every discovery period for transmitting sidelink discovery announcement(s).
discTxResourceReqPS
Indicates the number of separate public safety related discovery message(s) the UE wants to transmit every discovery period. This field concerns the resources the UE requires every discovery period for transmitting public safety related sidelink discovery announcement(s).
discSysInfoReportList
Indicates a list of acquired System Information from SIBs of cells on configured carrier frequencies.

-	SystemInformation
The SystemInformation message is used to convey one or more System Information Blocks. All the SIBs included are transmitted with the same periodicity.
Signalling radio bearer: N/A
RLC-SAP: TM
Logical channel: BCCH
Direction: E-UTRAN to UE
SystemInformation message
-- ASN1START

SystemInformation ::=				SEQUENCE {
	criticalExtensions					CHOICE {
		systemInformation-r8				SystemInformation-r8-IEs,
		criticalExtensionsFuture			SEQUENCE {}
	}
}
SystemInformation-r8-IEs ::=		SEQUENCE {
	sib-TypeAndInfo						SEQUENCE (SIZE (1..maxSIB)) OF CHOICE {
		sib2								SystemInformationBlockType2,
		sib3								SystemInformationBlockType3,
		sib4								SystemInformationBlockType4,
		sib5								SystemInformationBlockType5,
		sib6								SystemInformationBlockType6,
		sib7								SystemInformationBlockType7,
		sib8								SystemInformationBlockType8,
		sib9								SystemInformationBlockType9,
		sib10								SystemInformationBlockType10,
		sib11								SystemInformationBlockType11,
		...,
		sib12-v920							SystemInformationBlockType12-r9,
		sib13-v920							SystemInformationBlockType13-r9,
		sib14-v1130							SystemInformationBlockType14-r11,
		sib15-v1130							SystemInformationBlockType15-r11,
		sib16-v1130							SystemInformationBlockType16-r11,
		sib17-v1250							SystemInformationBlockType17-r12,
		sib18-v1250							SystemInformationBlockType18-r12,
		sib19-v1250							SystemInformationBlockType19-r12,
		sib20-v13x0							SystemInformationBlockType20-r13
	},
	nonCriticalExtension				SystemInformation-v8a0-IEs			OPTIONAL
}

SystemInformation-v8a0-IEs ::= SEQUENCE {
	lateNonCriticalExtension			OCTET STRING						OPTIONAL,
	nonCriticalExtension				SEQUENCE {}							OPTIONAL
}

-- ASN1STOP

-	SystemInformationBlockType1
SystemInformationBlockType1 contains information relevant when evaluating if a UE is allowed to access a cell and defines the scheduling of other system information.
Signalling radio bearer: N/A
RLC-SAP: TM
Logical channel: BCCH
Direction: E-UTRAN to UE
SystemInformationBlockType1 message
-- ASN1START

SystemInformationBlockType1 ::=		SEQUENCE {
	cellAccessRelatedInfo				SEQUENCE {
		plmn-IdentityList					PLMN-IdentityList,
		trackingAreaCode					TrackingAreaCode,
		cellIdentity						CellIdentity,
		cellBarred							ENUMERATED {barred, notBarred},
		intraFreqReselection				ENUMERATED {allowed, notAllowed},
		csg-Indication						BOOLEAN,
		csg-Identity						CSG-Identity			OPTIONAL	-- Need OR
	},
	cellSelectionInfo					SEQUENCE {
		q-RxLevMin							Q-RxLevMin,
		q-RxLevMinOffset					INTEGER (1..8)			OPTIONAL	-- Need OP
	},
	p-Max								P-Max						OPTIONAL,			-- Need OP
	freqBandIndicator					FreqBandIndicator,
	schedulingInfoList					SchedulingInfoList,
	tdd-Config							TDD-Config					OPTIONAL,	-- Cond TDD
	si-WindowLength						ENUMERATED {
											ms1, ms2, ms5, ms10, ms15, ms20,
											ms40},
	systemInfoValueTag					INTEGER (0..31),
	nonCriticalExtension				SystemInformationBlockType1-v890-IEs	OPTIONAL
}

SystemInformationBlockType1-v890-IEs::=	SEQUENCE {
	lateNonCriticalExtension			OCTET STRING (CONTAINING SystemInformationBlockType1-v8h0-IEs)			OPTIONAL,
	nonCriticalExtension				SystemInformationBlockType1-v920-IEs	OPTIONAL
}

-- Late non critical extensions
SystemInformationBlockType1-v8h0-IEs ::=	SEQUENCE {
	multiBandInfoList					MultiBandInfoList		OPTIONAL,	-- Need OR
	nonCriticalExtension				SystemInformationBlockType1-v9e0-IEs	OPTIONAL
}

SystemInformationBlockType1-v9e0-IEs ::= SEQUENCE {
	freqBandIndicator-v9e0				FreqBandIndicator-v9e0		OPTIONAL,	-- Cond FBI-max
	multiBandInfoList-v9e0				MultiBandInfoList-v9e0		OPTIONAL,	-- Cond mFBI-max
	nonCriticalExtension				SystemInformationBlockType1-v10j0-IEs	OPTIONAL
}

SystemInformationBlockType1-v10j0-IEs ::= SEQUENCE {
	freqBandInfo-r10					NS-PmaxList-r10				OPTIONAL,	-- Need OR
	multiBandInfoList-v10j0				MultiBandInfoList-v10j0		OPTIONAL,	-- Need OR
	nonCriticalExtension				SEQUENCE {}					OPTIONAL
}

-- Regular non critical extensions
SystemInformationBlockType1-v920-IEs ::=	SEQUENCE {
	ims-EmergencySupport-r9				ENUMERATED {true}			OPTIONAL,	-- Need OR
	cellSelectionInfo-v920				CellSelectionInfo-v920		OPTIONAL,	-- Cond RSRQ
	nonCriticalExtension				SystemInformationBlockType1-v1130-IEs	OPTIONAL
}

SystemInformationBlockType1-v1130-IEs ::=	SEQUENCE {
	tdd-Config-v1130				TDD-Config-v1130			OPTIONAL,	-- Cond TDD-OR
	cellSelectionInfo-v1130			CellSelectionInfo-v1130		OPTIONAL,	-- Cond WB-RSRQ
	nonCriticalExtension			SystemInformationBlockType1-v1250-IEs	OPTIONAL
}

SystemInformationBlockType1-v1250-IEs ::=	SEQUENCE {
	cellAccessRelatedInfo-v1250					SEQUENCE {
		category0Allowed-r12						ENUMERATED {true}		OPTIONAL	-- Need OP
	},
	cellSelectionInfo-v1250					CellSelectionInfo-v1250		OPTIONAL,	-- Cond RSRQ2
	freqBandIndicatorPriority-r12			ENUMERATED {true}			OPTIONAL,	-- Cond mFBI
	nonCriticalExtension			SystemInformationBlockType1-v13xy-IEs	OPTIONAL				
}

SystemInformationBlockType1-v13xy-IEs ::=	SEQUENCE {
	hyperSFN						BIT STRING (SIZE (10))		OPTIONAL,
	eDRXAllowed			ENUMERATED {true}		OPTIONAL, 
	nonCriticalExtension			SEQUENCE {}					OPTIONAL
}

PLMN-IdentityList ::=					SEQUENCE (SIZE (1..maxPLMN-r11)) OF PLMN-IdentityInfo

PLMN-IdentityInfo ::=					SEQUENCE {
	plmn-Identity							PLMN-Identity,
	cellReservedForOperatorUse				ENUMERATED {reserved, notReserved}
}

SchedulingInfoList ::= SEQUENCE (SIZE (1..maxSI-Message)) OF SchedulingInfo

SchedulingInfo ::=	SEQUENCE {
	si-Periodicity						ENUMERATED {
											rf8, rf16, rf32, rf64, rf128, rf256, rf512},
	sib-MappingInfo						SIB-MappingInfo
}

SIB-MappingInfo ::= SEQUENCE (SIZE (0..maxSIB-1)) OF SIB-Type

SIB-Type ::=						ENUMERATED {
										sibType3, sibType4, sibType5, sibType6,
										sibType7, sibType8, sibType9, sibType10,
										sibType11, sibType12-v920, sibType13-v920,
										sibType14-v1130, sibType15-v1130,
										sibType16-v1130, sibType17-v1250, sibType18-v1250,
										..., sibType19-v1250, sibType20-v13xy}

CellSelectionInfo-v920 ::=			SEQUENCE {
	q-QualMin-r9						Q-QualMin-r9,
	q-QualMinOffset-r9					INTEGER (1..8)						OPTIONAL	-- Need OP
}

CellSelectionInfo-v1130 ::=			SEQUENCE {
	q-QualMinWB-r11						Q-QualMin-r9
}

CellSelectionInfo-v1250 ::=			SEQUENCE {
	q-QualMinRSRQ-OnAllSymbols-r12						Q-QualMin-r9
}

-- ASN1STOP

SystemInformationBlockType1 field descriptions
category0Allowed
The presence of this field indicates category 0 UEs are allowed to access the cell.
cellBarred
barred means the cell is barred, as defined in TS 36.304 [4].
cellReservedForOperatorUse
As defined in TS 36.304 [4].
csg-Identity
Identity of the Closed Subscriber Group the cell belongs to.
csg-Indication
If set to TRUE the UE is only allowed to access the cell if it is a CSG member cell, if selected during manual CSG selection or to obtain limited service, see TS 36.304 [4].
eDRXAllowed
Indicates if idle mode extended DRX is allowed in the cell. The UE shall not operate in idle mode extended DRX unless eDRXAllowed  is set to TRUE.
freqBandIndicatorPriority
If the field is present and supported by the UE, the UE shall prioritize the frequency bands in the multiBandInfoList IE in decreasing priority order. Only if the UE does not support any of the frequency band in multiBandInfoList, the UE shall use the value in freqBandIndicator IE. Otherwise, the UE applies frequency band according to the rules defined in multiBandInfoList.
freqBandInfo
A list of additionalPmax and additionalSpectrumEmission values as defined in TS 36.101 [42, table 6.2.4-1] for the frequency band in freqBandIndicator.
hyperSFN
Indicates hyper SFN which increments by one when the SFN wraps around.
ims-EmergencySupport
Indicates whether the cell supports IMS emergency bearer services for UEs in limited service mode. If absent, IMS emergency call is not supported by the network in the cell for UEs in limited service mode.
intraFreqReselection
Used to control cell reselection to intra-frequency cells when the highest ranked cell is barred, or treated as barred by the UE, as specified in TS 36.304 [4].
multiBandInfoList
A list of additional frequency band indicators, as defined in TS 36.101 [42, table 5.5-1] that the cell belongs to. If the UE supports the frequency band in the freqBandIndicator IE it shall apply that frequency band. Otherwise, the UE shall apply the first listed band which it supports in the multiBandInfoList IE. If E-UTRAN includes multiBandInfoList-v9e0 it includes the same number of entries, and listed in the same order, as in multiBandInfoList (i.e. without suffix). See Annex D for more descriptions. The UE shall ignore the rule defined in this field description if freqBandIndicatorPriority is present and supported by the UE.
multiBandInfoList-v10j0
A list of additionalPmax and additionalSpectrumEmission values as defined in TS 36.101 [42, table 6.2.4-1] for the frequency bands in multiBandInfoList (i.e. without suffix) and multiBandInfoList-v9e0. If E-UTRAN includes multiBandInfoList-v10j0, it includes the same number of entries, and listed in the same order, as in multiBandInfoList (i.e. without suffix).
plmn-IdentityList
List of PLMN identities. The first listed PLMN-Identity is the primary PLMN.
p-Max
Value applicable for the cell. If absent the UE applies the maximum power according to the UE capability.
q-QualMin
Parameter "Qqualmin" in TS 36.304 [4]. If cellSelectionInfo-v920 is not present, the UE applies the (default) value of negative infinity for Qqualmin. NOTE 1.
q-QualMinRSRQ-OnAllSymbols
If this field is present and supported by the UE, the UE shall, when performing RSRQ measurements, perform RSRQ measurement on all OFDM symbols in accordance with TS 36.214 [48]. NOTE 1.
q-QualMinOffset
Parameter "Qqualminoffset" in TS 36.304 [4]. Actual value Qqualminoffset = IE value [dB]. If cellSelectionInfo-v920 is not present or the field is not present, the UE applies the (default) value of 0 dB for Qqualminoffset. Affects the minimum required quality level in the cell.
q-QualMinWB
If this field is present and supported by the UE, the UE shall, when performing RSRQ measurements, use a wider bandwidth in accordance with TS 36.133 [16]. NOTE 1.
q-RxLevMinOffset
Parameter Qrxlevminoffset in TS 36.304 [4]. Actual value Qrxlevminoffset = IE value * 2 [dB]. If absent, the UE applies the (default) value of 0 dB for Qrxlevminoffset. Affects the minimum required Rx level in the cell.
sib-MappingInfo
List of the SIBs mapped to this SystemInformation message.There is no mapping information of SIB2; it is always present in the first SystemInformation message listed in the schedulingInfoList list.
si-Periodicity
Periodicity of the SI-message in radio frames, such that rf8 denotes 8 radio frames, rf16 denotes 16 radio frames, and so on.
si-WindowLength
Common SI scheduling window for all SIs. Unit in milliseconds, where ms1 denotes 1 millisecond, ms2 denotes 2 milliseconds and so on.
systemInfoValueTag
Common for all SIBs other than MIB, SIB1, SIB10, SIB11, SIB12 and SIB14. Change of MIB and SIB1 is detected by acquisition of the corresponding message.
trackingAreaCode
A trackingAreaCode that is common for all the PLMNs listed.

NOTE 1:	The value the UE applies for parameter "Qqualmin" in TS 36.304 [4] depends on the q-QualMin fields signalled by E-UTRAN and supported by the UE. In case multiple candidate options are available, the UE shall select the highest priority candidate option according to the priority order indicated by the following table (top row is highest priority).
q-QualMinRSRQ-OnAllSymbols
q-QualMinWB
Value of parameter "Qqualmin" in TS 36.304 [4]
Included
Included
q-QualMinRSRQ-OnAllSymbols - (q-QualMin - q-QualMinWB)
Included
Not included
q-QualMinRSRQ-OnAllSymbols
Not included
Included
q-QualMinWB
Not included
Not included
q-QualMin

Conditional presence
Explanation
FBI-max
The field is mandatory present if freqBandIndicator (i.e. without suffix) is set to maxFBI. Otherwise the field is not present.
mFBI
The field is optional present, Need OR, if multiBandInfoList is present. Otherwise the field is not present.
mFBI-max
The field is mandatory present if one or more entries in multiBandInfoList (i.e. without suffix, introduced in -v8h0) is set to maxFBI. Otherwise the field is not present.
RSRQ
The field is mandatory present if SIB3 is being broadcast and threshServingLowQ is present in SIB3; otherwise optionally present, Need OP.
RSRQ2
The field is mandatory present if q-QualMinRSRQ-OnAllSymbols is present in SIB3; otherwise it is not present and the UE shall delete any existing value for this field.
TDD
This field is mandatory present for TDD; it is not present for FDD and the UE shall delete any existing value for this field.
TDD-OR
The field is optional present for TDD, need OR; it is not present for FDD.
WB-RSRQ
The field is optionally present, need OP if the measurement bandwidth indicated by allowedMeasBandwidth in systemInformationBlockType3 is 50 resource blocks or larger; otherwise it is not present.

-	UEAssistanceInformation
The UEAssistanceInformation message is used for the indication of UE assistance information to the eNB.
Signalling radio bearer: SRB1
RLC-SAP: AM
Logical channel: DCCH
Direction: UE to E-UTRAN
UEAssistanceInformation message
-- ASN1START

UEAssistanceInformation-r11 ::=				SEQUENCE {
	criticalExtensions					CHOICE {
		c1									CHOICE {
			ueAssistanceInformation-r11			UEAssistanceInformation-r11-IEs,
			spare3 NULL, spare2 NULL, spare1 NULL
		},
		criticalExtensionsFuture			SEQUENCE {}
	}
}

UEAssistanceInformation-r11-IEs ::=		SEQUENCE {
	powerPrefIndication-r11				ENUMERATED	{normal, lowPowerConsumption}	OPTIONAL,
	lateNonCriticalExtension			OCTET STRING						OPTIONAL,
	nonCriticalExtension				SEQUENCE {}							OPTIONAL
}

-- ASN1STOP

UEAssistanceInformation field descriptions
powerPrefIndication
Value lowPowerConsumption indicates the UE prefers a configuration that is primarily optimised for power saving. Otherwise the value is set to normal.

-	UECapabilityEnquiry
The UECapabilityEnquiry message is used to request the transfer of UE radio access capabilities for E-UTRA as well as for other RATs.
Signalling radio bearer: SRB1
RLC-SAP: AM
Logical channel: DCCH
Direction: E-UTRAN to UE
UECapabilityEnquiry message
-- ASN1START

UECapabilityEnquiry ::=				SEQUENCE {
	rrc-TransactionIdentifier			RRC-TransactionIdentifier,
	criticalExtensions					CHOICE {
		c1									CHOICE {
			ueCapabilityEnquiry-r8				UECapabilityEnquiry-r8-IEs,
			spare3 NULL, spare2 NULL, spare1 NULL
		},
		criticalExtensionsFuture			SEQUENCE {}
	}
}

UECapabilityEnquiry-r8-IEs ::=		SEQUENCE {
	ue-CapabilityRequest				UE-CapabilityRequest,
	nonCriticalExtension				UECapabilityEnquiry-v8a0-IEs		OPTIONAL
}

UECapabilityEnquiry-v8a0-IEs ::= SEQUENCE {
	lateNonCriticalExtension			OCTET STRING						OPTIONAL,
	nonCriticalExtension				UECapabilityEnquiry-v1180-IEs							OPTIONAL
}

UECapabilityEnquiry-v1180-IEs ::= SEQUENCE {
	requestedFrequencyBands-r11			SEQUENCE (SIZE (1..16)) OF FreqBandIndicator-r11							OPTIONAL,
	nonCriticalExtension				UECapabilityEnquiry-v13xy-IEs 							OPTIONAL
}

UECapabilityEnquiry-v13xy-IEs ::= SEQUENCE {
	requestReducedFormat-r13			ENUMERATED {true}					OPTIONAL,
	skipFallbackCombinations-r13		ENUMERATED {true}					OPTIONAL,
	requestedMaxCCsDL-r13			INTEGER (2..32)						OPTIONAL,
	requestedMaxCCsUL-r13			INTEGER (2..32)						OPTIONAL,
	nonCriticalExtension				SEQUENCE {}							OPTIONAL
}

UE-CapabilityRequest ::=		SEQUENCE (SIZE (1..maxRAT-Capabilities)) OF RAT-Type

-- ASN1STOP

UECapabilityEnquiry field descriptions
requestReducedFormat
Indicates that the UE if supported is requested to provide supported CA band combinations in the supportedBandCombinations-r13 instead of the supportedBandCombination-r10.
skipFallbackCombinations
Indicates that the UE shall explicitly exclude fallback CA band combinations in capability signalling. 
ue-CapabilityRequest
List of the RATs for which the UE is requested to transfer the UE radio access capabilities i.e. E-UTRA, UTRA, GERAN-CS, GERAN-PS, CDMA2000.
requestedFrequencyBands
List of frequency bands for which the UE is requested to provide supported CA band combinations and non CA bands.
requestedMaxCCsDL, requestedMaxCCsUL
Indicates the maximum number of CCs for which the UE is requested to provide supported CA band combinations and non-CA bands.

-	UECapabilityInformation
The UECapabilityInformation message is used to transfer of UE radio access capabilities requested by the E-UTRAN.
Signalling radio bearer: SRB1
RLC-SAP: AM
Logical channel: DCCH
Direction: UE to E-UTRAN
UECapabilityInformation message
-- ASN1START

UECapabilityInformation ::=			SEQUENCE {
	rrc-TransactionIdentifier			RRC-TransactionIdentifier,
	criticalExtensions					CHOICE {
		c1									CHOICE{
			ueCapabilityInformation-r8			UECapabilityInformation-r8-IEs,
			spare7 NULL,
			spare6 NULL, spare5 NULL, spare4 NULL,
			spare3 NULL, spare2 NULL, spare1 NULL
		},
		criticalExtensionsFuture			SEQUENCE {}
	}
}

UECapabilityInformation-r8-IEs ::=	SEQUENCE {
	ue-CapabilityRAT-ContainerList		UE-CapabilityRAT-ContainerList,
	nonCriticalExtension				UECapabilityInformation-v8a0-IEs	OPTIONAL
}

UECapabilityInformation-v8a0-IEs ::= SEQUENCE {
	lateNonCriticalExtension			OCTET STRING						OPTIONAL,
	nonCriticalExtension				UECapabilityInformation-v1250-IEs	OPTIONAL
}

UECapabilityInformation-v1250-IEs ::= SEQUENCE {
	ue-RadioPagingInfo-r12				UE-RadioPagingInfo-r12				OPTIONAL,
	nonCriticalExtension				SEQUENCE {}							OPTIONAL
}

-- ASN1STOP

UECapabilityInformation field descriptions 
ue-RadioPagingInfo
This field contains information used for paging of category 0 UEs.

-	UEInformationRequest
The UEInformationRequest is the command used by E-UTRAN to retrieve information from the UE. 
Signalling radio bearer: SRB1
RLC-SAP: AM
Logical channel: DCCH
Direction: E-UTRAN to UE
UEInformationRequest message
-- ASN1START

UEInformationRequest-r9		::=				SEQUENCE {
	rrc-TransactionIdentifier		RRC-TransactionIdentifier,
	criticalExtensions				CHOICE {
		c1								CHOICE {
			ueInformationRequest-r9				UEInformationRequest-r9-IEs,
			spare3 NULL, spare2 NULL, spare1 NULL
		},
		criticalExtensionsFuture			SEQUENCE {}
	}
}

UEInformationRequest-r9-IEs ::=		SEQUENCE {
	rach-ReportReq-r9					BOOLEAN,
	rlf-ReportReq-r9					BOOLEAN,
	nonCriticalExtension				UEInformationRequest-v930-IEs		OPTIONAL
}

UEInformationRequest-v930-IEs ::= SEQUENCE {
	lateNonCriticalExtension			OCTET STRING						OPTIONAL,
	nonCriticalExtension				UEInformationRequest-v1020-IEs		OPTIONAL
}

UEInformationRequest-v1020-IEs ::=	SEQUENCE {
	logMeasReportReq-r10				ENUMERATED {true}					OPTIONAL,	-- Need ON
	nonCriticalExtension				UEInformationRequest-v1130-IEs		OPTIONAL
}

UEInformationRequest-v1130-IEs ::= SEQUENCE {
	connEstFailReportReq-r11			ENUMERATED {true}					OPTIONAL,	-- Need ON
	nonCriticalExtension				UEInformationRequest-v1250-IEs		OPTIONAL
}

UEInformationRequest-v1250-IEs ::= SEQUENCE {
	mobilityHistoryReportReq-r12		ENUMERATED {true}					OPTIONAL,	-- Need ON
	nonCriticalExtension				SEQUENCE {}							OPTIONAL
}

-- ASN1STOP

UEInformationRequest field descriptions
rach-ReportReq
This field is used to indicate whether the UE shall report information about the random access procedure.

-	UEInformationResponse
The UEInformationResponse message is used by the UE to transfer the information requested by the E-UTRAN.
Signalling radio bearer: SRB1 or SRB2 (when logged measurement information is included)
RLC-SAP: AM
Logical channel: DCCH
Direction: UE to E-UTRAN
UEInformationResponse message
-- ASN1START

UEInformationResponse-r9	::=			SEQUENCE {
	rrc-TransactionIdentifier			RRC-TransactionIdentifier,
	criticalExtensions					CHOICE {
		c1								CHOICE {
			ueInformationResponse-r9				UEInformationResponse-r9-IEs,
			spare3 NULL, spare2 NULL, spare1 NULL
		},
		criticalExtensionsFuture				SEQUENCE {}
	}
}

UEInformationResponse-r9-IEs ::=		SEQUENCE {
	rach-Report-r9							SEQUENCE {
		numberOfPreamblesSent-r9				NumberOfPreamblesSent-r11,
		contentionDetected-r9					BOOLEAN
	}																OPTIONAL,
	rlf-Report-r9							RLF-Report-r9			OPTIONAL,
	nonCriticalExtension					UEInformationResponse-v930-IEs				OPTIONAL
}

-- Late non critical extensions
UEInformationResponse-v9e0-IEs ::= SEQUENCE {
	rlf-Report-v9e0						RLF-Report-v9e0					OPTIONAL,
	nonCriticalExtension				SEQUENCE {}						OPTIONAL
}

-- Regular non critical extensions
UEInformationResponse-v930-IEs ::=	SEQUENCE {
	lateNonCriticalExtension			OCTET STRING (CONTAINING UEInformationResponse-v9e0-IEs)	OPTIONAL,
	nonCriticalExtension				UEInformationResponse-v1020-IEs		OPTIONAL
}

UEInformationResponse-v1020-IEs ::= SEQUENCE {
	logMeasReport-r10					LogMeasReport-r10				OPTIONAL,
	nonCriticalExtension				UEInformationResponse-v1130-IEs		OPTIONAL
}

UEInformationResponse-v1130-IEs ::= SEQUENCE {
	connEstFailReport-r11				ConnEstFailReport-r11			OPTIONAL,
	nonCriticalExtension				UEInformationResponse-v1250-IEs	OPTIONAL
}

UEInformationResponse-v1250-IEs ::= SEQUENCE {
	mobilityHistoryReport-r12			MobilityHistoryReport-r12		OPTIONAL,
	nonCriticalExtension				SEQUENCE {}						OPTIONAL
}

RLF-Report-r9 ::= 					SEQUENCE {
	measResultLastServCell-r9				SEQUENCE {
		rsrpResult-r9							RSRP-Range,
		rsrqResult-r9							RSRQ-Range			OPTIONAL
	},
	measResultNeighCells-r9				SEQUENCE {
		measResultListEUTRA-r9				MeasResultList2EUTRA-r9			OPTIONAL,
		measResultListUTRA-r9				MeasResultList2UTRA-r9			OPTIONAL,
		measResultListGERAN-r9				MeasResultListGERAN				OPTIONAL,
		measResultsCDMA2000-r9				MeasResultList2CDMA2000-r9		OPTIONAL
	}	OPTIONAL,
	...,
	[[	locationInfo-r10				LocationInfo-r10		OPTIONAL,
		failedPCellId-r10						CHOICE {
			cellGlobalId-r10						CellGlobalIdEUTRA,
			pci-arfcn-r10							SEQUENCE {
				physCellId-r10							PhysCellId,
				carrierFreq-r10							ARFCN-ValueEUTRA
			}
		}																OPTIONAL,
		reestablishmentCellId-r10		CellGlobalIdEUTRA				OPTIONAL,
		timeConnFailure-r10				INTEGER (0..1023)				OPTIONAL,
		connectionFailureType-r10		ENUMERATED {rlf, hof}			OPTIONAL,
		previousPCellId-r10				CellGlobalIdEUTRA				OPTIONAL
	]],
	[[	failedPCellId-v1090				SEQUENCE {
			carrierFreq-v1090				ARFCN-ValueEUTRA-v9e0
		}																OPTIONAL
	]],
	[[	basicFields-r11					SEQUENCE {
			c-RNTI-r11						C-RNTI,
			rlf-Cause-r11					ENUMERATED {
												t310-Expiry, randomAccessProblem,
												rlc-MaxNumRetx, t312-Expiry-r12},
			timeSinceFailure-r11			TimeSinceFailure-r11
		}																OPTIONAL,
		previousUTRA-CellId-r11			SEQUENCE {
			carrierFreq-r11					ARFCN-ValueUTRA,
			physCellId-r11					CHOICE {
				fdd-r11							PhysCellIdUTRA-FDD,
				tdd-r11							PhysCellIdUTRA-TDD
			},
			cellGlobalId-r11				CellGlobalIdUTRA			OPTIONAL
		}																OPTIONAL,
		selectedUTRA-CellId-r11			SEQUENCE {
			carrierFreq-r11					ARFCN-ValueUTRA,
			physCellId-r11					CHOICE {
				fdd-r11							PhysCellIdUTRA-FDD,
				tdd-r11							PhysCellIdUTRA-TDD
			}
		}																OPTIONAL
	]],
	[[	failedPCellId-v1250				SEQUENCE {
			tac-FailedPCell-r12			TrackingAreaCode				
		}																OPTIONAL,
		measResultLastServCell-v1250	RSRQ-Range-v1250				OPTIONAL,
		lastServCellRSRQ-Type-r12		RSRQ-Type-r12					OPTIONAL,
		measResultListEUTRA-v1250		MeasResultList2EUTRA-v1250		OPTIONAL
	]],
	[[	droppedQCI-r13					ENUMERATED {qci1}				OPTIONAL
	]]
}

RLF-Report-v9e0 ::= 				SEQUENCE {
	measResultListEUTRA-v9e0			MeasResultList2EUTRA-v9e0
}

MeasResultList2EUTRA-r9 ::=				SEQUENCE (SIZE (1..maxFreq)) OF MeasResult2EUTRA-r9

MeasResultList2EUTRA-v9e0 ::=			SEQUENCE (SIZE (1..maxFreq)) OF MeasResult2EUTRA-v9e0

MeasResultList2EUTRA-v1250 ::=			SEQUENCE (SIZE (1..maxFreq)) OF MeasResult2EUTRA-v1250

MeasResult2EUTRA-r9 ::=				SEQUENCE {
	carrierFreq-r9						ARFCN-ValueEUTRA,
	measResultList-r9					MeasResultListEUTRA
}

MeasResult2EUTRA-v9e0 ::=				SEQUENCE {
	carrierFreq-v9e0						ARFCN-ValueEUTRA-v9e0		OPTIONAL
}

MeasResult2EUTRA-v1250 ::=				SEQUENCE {
	rsrq-Type-r12							RSRQ-Type-r12		OPTIONAL
}

MeasResultList2UTRA-r9 ::=			SEQUENCE (SIZE (1..maxFreq)) OF MeasResult2UTRA-r9

MeasResult2UTRA-r9 ::=				SEQUENCE {
	carrierFreq-r9						ARFCN-ValueUTRA,
	measResultList-r9					MeasResultListUTRA
}

MeasResultList2CDMA2000-r9 ::=		SEQUENCE (SIZE (1..maxFreq)) OF MeasResult2CDMA2000-r9

MeasResult2CDMA2000-r9 ::= 			SEQUENCE {
	carrierFreq-r9						CarrierFreqCDMA2000,
	measResultList-r9					MeasResultsCDMA2000
}

LogMeasReport-r10 ::= 				SEQUENCE {
	absoluteTimeStamp-r10				AbsoluteTimeInfo-r10,
	traceReference-r10					TraceReference-r10,
	traceRecordingSessionRef-r10		OCTET STRING (SIZE (2)),
	tce-Id-r10							OCTET STRING (SIZE (1)),
	logMeasInfoList-r10					LogMeasInfoList-r10,
	logMeasAvailable-r10				ENUMERATED {true}				OPTIONAL,
	...
}

LogMeasInfoList-r10 ::= 		SEQUENCE (SIZE (1..maxLogMeasReport-r10)) OF LogMeasInfo-r10

LogMeasInfo-r10 ::= 		SEQUENCE {
	locationInfo-r10					LocationInfo-r10		OPTIONAL,
	relativeTimeStamp-r10				INTEGER (0..7200),
	servCellIdentity-r10				CellGlobalIdEUTRA,
	measResultServCell-r10				SEQUENCE {
		rsrpResult-r10						RSRP-Range,
		rsrqResult-r10						RSRQ-Range
	},
	measResultNeighCells-r10			SEQUENCE {
		measResultListEUTRA-r10				MeasResultList2EUTRA-r9		OPTIONAL,
		measResultListUTRA-r10				MeasResultList2UTRA-r9		OPTIONAL,
		measResultListGERAN-r10				MeasResultList2GERAN-r10	OPTIONAL,
		measResultListCDMA2000-r10			MeasResultList2CDMA2000-r9	OPTIONAL
	}	OPTIONAL,
	...,
	[[	measResultListEUTRA-v1090			MeasResultList2EUTRA-v9e0	OPTIONAL
	]],
	[[	measResultListMBSFN-r12				MeasResultListMBSFN-r12	OPTIONAL,
		measResultServCell-v1250			RSRQ-Range-v1250			OPTIONAL,
		servCellRSRQ-Type-r12				RSRQ-Type-r12				OPTIONAL,
		measResultListEUTRA-v1250			MeasResultList2EUTRA-v1250	OPTIONAL
	]],
	[[	inDeviceCoexDetected-r13			ENUMERATED {true}			OPTIONAL
	]]
}

MeasResultListMBSFN-r12 ::= 			SEQUENCE (SIZE (1..maxMBSFN-Area)) OF MeasResultMBSFN-r12

MeasResultMBSFN-r12 ::= 			SEQUENCE {
	mbsfn-Area-r12							SEQUENCE {
		mbsfn-AreaId-r12						MBSFN-AreaId-r12,
		carrierFreq-r12							ARFCN-ValueEUTRA-r9
	},
	rsrpResultMBSFN-r12						RSRP-Range,
	rsrqResultMBSFN-r12						MBSFN-RSRQ-Range-r12,
	signallingBLER-Result-r12				BLER-Result-r12				OPTIONAL,
	dataBLER-MCH-ResultList-r12				DataBLER-MCH-ResultList-r12	OPTIONAL,
	...
}

DataBLER-MCH-ResultList-r12 ::=			SEQUENCE (SIZE (1.. maxPMCH-PerMBSFN)) OF DataBLER-MCH-Result-r12

DataBLER-MCH-Result-r12 ::= 			SEQUENCE {
	mch-Index-r12							INTEGER (1..maxPMCH-PerMBSFN),
	dataBLER-Result-r12						BLER-Result-r12
}

BLER-Result-r12 ::=					SEQUENCE {
	bler-r12									BLER-Range-r12,
	blocksReceived-r12						SEQUENCE {
		n-r12									BIT STRING (SIZE (3)),		
		m-r12									BIT STRING (SIZE (8))
	}
}

BLER-Range-r12 ::=						INTEGER(0..31)

MeasResultList2GERAN-r10 ::=			SEQUENCE (SIZE (1..maxCellListGERAN)) OF MeasResultListGERAN

ConnEstFailReport-r11 ::= 				SEQUENCE {
	failedCellId-r11					CellGlobalIdEUTRA,
	locationInfo-r11					LocationInfo-r10				OPTIONAL,
	measResultFailedCell-r11				SEQUENCE {
		rsrpResult-r11							RSRP-Range,
		rsrqResult-r11							RSRQ-Range				OPTIONAL
	},
	measResultNeighCells-r11				SEQUENCE {
		measResultListEUTRA-r11				MeasResultList2EUTRA-r9			OPTIONAL,
		measResultListUTRA-r11				MeasResultList2UTRA-r9			OPTIONAL,
		measResultListGERAN-r11				MeasResultListGERAN				OPTIONAL,
		measResultsCDMA2000-r11				MeasResultList2CDMA2000-r9		OPTIONAL
	}	OPTIONAL,
	numberOfPreamblesSent-r11			NumberOfPreamblesSent-r11,
	contentionDetected-r11				BOOLEAN,
	maxTxPowerReached-r11				BOOLEAN,
	timeSinceFailure-r11				TimeSinceFailure-r11,
	measResultListEUTRA-v1130			MeasResultList2EUTRA-v9e0		OPTIONAL,
	...,
	[[	measResultFailedCell-v1250		RSRQ-Range-v1250				OPTIONAL,
		failedCellRSRQ-Type-r12			RSRQ-Type-r12					OPTIONAL,
		measResultListEUTRA-v1250		MeasResultList2EUTRA-v1250		OPTIONAL
	]]
}

NumberOfPreamblesSent-r11::=			INTEGER (1..200)

TimeSinceFailure-r11 ::=				INTEGER (0..172800)

MobilityHistoryReport-r12 ::=	VisitedCellInfoList-r12

-- ASN1STOP

UEInformationResponse field descriptions
absoluteTimeStamp
Indicates the absolute time when the logged measurement configuration logging is provided, as indicated by E-UTRAN within absoluteTimeInfo.
bler
Indicates the measured BLER value.
The coding of BLER value is defined in TS 36.133 [16].
blocksReceived
Indicates total number of MCH blocks, which were received by the UE and used for the corresponding BLER calculation, within the measurement period as defined in TS 36.133 [16].
carrierFreq
In case the UE includes carrierFreq-v9e0 and/ or carrierFreq-v1090, the UE shall set the corresponding entry of carrierFreq-r9 and/ or carrierFreq-r10 respectively to maxEARFCN. For E-UTRA and UTRA frequencies, the UE sets the ARFCN according to the band used when obtaining the concerned measurement results.
connectionFailureType
This field is used to indicate whether the connection failure is due to radio link failure or handover failure.
contentionDetected
This field is used to indicate that contention was detected for at least one of the transmitted preambles, see TS 36.321 [6]. 
c-RNTI
This field indicates the C-RNTI used in the PCell upon detecting radio link failure or the C-RNTI used in the source PCell upon handover failure.
droppedQCI
This field is used to indicate the radio link failure concerned bearer with QCI value equal 1, see TS 24.301 [35].
dataBLER-MCH-ResultList
Includes a BLER result per MCH on subframes using dataMCS, with the applicable MCH(s) listed in the same order as in pmch-InfoList within MBSFNAreaConfiguration.
failedCellId
This field is used to indicate the cell in which connection establishment failed.
failedPCellId
This field is used to indicate the PCell in which RLF is detected or the target PCell of the failed handover. The UE sets the EARFCN according to the band used for transmission/ reception when the failure occurred.
inDeviceCoexDetected
Indicates the reason for measurement logging suspension due to IDC problem detection.
maxTxPowerReached
This field is used to indicate whether or not the maximum power level was used for the last transmitted preamble, see TS 36.321 [6].
mch-Index
Indicates the MCH by referring to the entry as listed in pmch-InfoList within MBSFNAreaConfiguration.
measResultFailedCell
This field refers to the last measurement results taken in the cell, where connection establishment failure happened.
measResultLastServCell
This field refers to the last measurement results taken in the PCell, where radio link failure or handover failure happened.
measResultListEUTRA
If measResultListEUTRA-v9e0, measResultListEUTRA-v1090 or measResultListEUTRA-v1130 is included, the UE shall include the same number of entries, and listed in the same order, as in measResultListEUTRA-r9, measResultListEUTRA-r10 and/ or measResultListEUTRA-r11 respectively.
measResultListEUTRA-v1250
If included in RLF-Report-r9 the UE shall include the same number of entries, and listed in the same order, as in measResultListEUTRA-r9;
If included in LogMeasInfo-r10 the UE shall include the same number of entries, and listed in the same order, as in measResultListEUTRA-r10;
If included in ConnEstFailReport-r11 the UE shall include the same number of entries, and listed in the same order, as in measResultListEUTRA-r11;
mobilityHistoryReport
This field is used to indicate the time of stay in 16 most recently visited E-UTRA cells or of stay out of E-UTRA.
numberOfPreamblesSent
This field is used to indicate the number of RACH preambles that were transmitted. Corresponds to parameter PREAMBLE_TRANSMISSION_COUNTER in TS 36.321 [6].
previousPCellId
This field is used to indicate the source PCell of the last handover (source PCell when the last RRC-Connection-Reconfiguration message including mobilityControlInfowas received).
previousUTRA-CellId
This field is used to indicate the source UTRA cell of the last successful handover to E-UTRAN, when RLF occurred at the target PCell. The UE sets the ARFCN according to the band used for transmission/ reception on the concerned cell.
reestablishmentCellId
This field is used to indicate the cell in which the re-establishment attempt was made after connection failure.
relativeTimeStamp
Indicates the time of logging measurement results, measured relative to the absoluteTimeStamp. Value in seconds.
rlf-Cause
This field is used to indicate the cause of the last radio link failure that was detected. In case of handover failure information reporting (i.e., the connectionFailureType is set to 'hof'), the UE is allowed to set this field to any value.
selectedUTRA-CellId
This field is used to indicate the UTRA cell that the UE selects after RLF is detected, while T311 is running. The UE sets the ARFCN according to the band selected for transmission/ reception on the concerned cell.
signallingBLER-Result
Includes a BLER result of MBSFN subframes using signallingMCS. 
tac-FailedPCell
This field is used to indicate the Tracking Area Code of the PCell in which RLF is detected.
tce-Id
Parameter Trace Collection Entity Id: See TS 32.422 [58].
timeConnFailure
This field is used to indicate the time elapsed since the last HO initialization until connection failure. Actual value = IE value * 100ms. The maximum value 1023 means 102.3s or longer.
timeSinceFailure
This field is used to indicate the time that elapsed since the connection (establishment) failure. Value in seconds. The maximum value 172800 means 172800s or longer.
traceRecordingSessionRef
Parameter Trace Recording Session Reference: See TS 32.422 [58].

-	ULHandoverPreparationTransfer (CDMA2000)
The ULHandoverPreparationTransfer message is used for the uplink transfer of handover related CDMA2000 information when requested by the higher layers.
Signalling radio bearer: SRB1
RLC-SAP: AM
Logical channel: DCCH
Direction: UE to E-UTRAN
ULHandoverPreparationTransfer message
-- ASN1START

ULHandoverPreparationTransfer ::=	SEQUENCE {
	criticalExtensions					CHOICE {
		c1									CHOICE {
			ulHandoverPreparationTransfer-r8		ULHandoverPreparationTransfer-r8-IEs,
			spare3 NULL, spare2 NULL, spare1 NULL
		},
		criticalExtensionsFuture				SEQUENCE {}
	}
}

ULHandoverPreparationTransfer-r8-IEs ::= SEQUENCE {
	cdma2000-Type						CDMA2000-Type,
	meid								BIT STRING (SIZE (56))	OPTIONAL,
	dedicatedInfo						DedicatedInfoCDMA2000,
	nonCriticalExtension				ULHandoverPreparationTransfer-v8a0-IEs	OPTIONAL
}

ULHandoverPreparationTransfer-v8a0-IEs ::= SEQUENCE {
	lateNonCriticalExtension			OCTET STRING						OPTIONAL,
	nonCriticalExtension				SEQUENCE {}							OPTIONAL
}

-- ASN1STOP

ULHandoverPreparationTransfer field descriptions
meid
The 56 bit mobile identification number provided by the CDMA2000 Upper layers.

-	ULInformationTransfer
The ULInformationTransfer message is used for the uplink transfer of NAS or non-3GPP dedicated information.
Signalling radio bearer: SRB2 or SRB1(only if SRB2 not established yet). If SRB2 is suspended, the UE does not send this message until SRB2 is resumed
RLC-SAP: AM
Logical channel: DCCH
Direction: UE to E-UTRAN
ULInformationTransfer message
-- ASN1START

ULInformationTransfer ::=			SEQUENCE {
	criticalExtensions					CHOICE {
		c1									CHOICE {
			ulInformationTransfer-r8			ULInformationTransfer-r8-IEs,
			spare3 NULL, spare2 NULL, spare1 NULL
		},
		criticalExtensionsFuture			SEQUENCE {}
	}
}

ULInformationTransfer-r8-IEs ::=	SEQUENCE {
	dedicatedInfoType			CHOICE {
		dedicatedInfoNAS					DedicatedInfoNAS,
		dedicatedInfoCDMA2000-1XRTT			DedicatedInfoCDMA2000,
		dedicatedInfoCDMA2000-HRPD			DedicatedInfoCDMA2000
	},
	nonCriticalExtension				ULInformationTransfer-v8a0-IEs							OPTIONAL
}

ULInformationTransfer-v8a0-IEs ::= SEQUENCE {
	lateNonCriticalExtension			OCTET STRING						OPTIONAL,
	nonCriticalExtension				SEQUENCE {}							OPTIONAL
}

-- ASN1STOP

6.3	RRC information elements
6.3.1	System information blocks
-	SystemInformationBlockType2
The IE SystemInformationBlockType2 contains radio resource configuration information that is common for all UEs.
NOTE:	UE timers and constants related to functionality for which parameters are provided in another SIB are included in the corresponding SIB.
SystemInformationBlockType2 information element
-- ASN1START

SystemInformationBlockType2 ::=		SEQUENCE {
	ac-BarringInfo						SEQUENCE {
		ac-BarringForEmergency				BOOLEAN,
		ac-BarringForMO-Signalling			AC-BarringConfig				OPTIONAL,	-- Need OP
		ac-BarringForMO-Data				AC-BarringConfig				OPTIONAL	-- Need OP
	}																		OPTIONAL,	-- Need OP
	radioResourceConfigCommon			RadioResourceConfigCommonSIB,
	ue-TimersAndConstants				UE-TimersAndConstants,
	freqInfo							SEQUENCE {
		ul-CarrierFreq						ARFCN-ValueEUTRA				OPTIONAL,	-- Need OP
		ul-Bandwidth						ENUMERATED {n6, n15, n25, n50, n75, n100}
																			OPTIONAL,	-- Need OP
		additionalSpectrumEmission			AdditionalSpectrumEmission
	},
	mbsfn-SubframeConfigList			MBSFN-SubframeConfigList			OPTIONAL, 	-- Need OR
	timeAlignmentTimerCommon			TimeAlignmentTimer,
	...,
	lateNonCriticalExtension		OCTET STRING (CONTAINING SystemInformationBlockType2-v8h0-IEs)						OPTIONAL,
	[[	ssac-BarringForMMTEL-Voice-r9		AC-BarringConfig				OPTIONAL,	-- Need OP
		ssac-BarringForMMTEL-Video-r9		AC-BarringConfig				OPTIONAL	-- Need OP
	]],
	[[	ac-BarringForCSFB-r10				AC-BarringConfig			OPTIONAL	-- Need OP
	]],
	[[	ac-BarringSkipForMMTELVoice-r12		ENUMERATED {true}			OPTIONAL,	 -- Need OP
		ac-BarringSkipForMMTELVideo-r12		ENUMERATED {true}			OPTIONAL,	 -- Need OP
		ac-BarringSkipForSMS-r12			ENUMERATED {true}			OPTIONAL,	 -- Need OP
		ac-BarringPerPLMN-List-r12			AC-BarringPerPLMN-List-r12	OPTIONAL	-- Need OP
	]],
	[[	voiceServiceCauseIndication-r12		ENUMERATED {true}			OPTIONAL	-- Need OP
	]],
	[[	acdc-BarringForCommon-r13			ACDC-BarringForCommon-r13		OPTIONAL,	-- Need OP
		acdc-BarringPerPLMN-List-r13		ACDC-BarringPerPLMN-List-r13	OPTIONAL	-- Need OP
	]]
}

SystemInformationBlockType2-v8h0-IEs ::=	SEQUENCE {
	multiBandInfoList				SEQUENCE (SIZE (1..maxMultiBands)) OF AdditionalSpectrumEmission	OPTIONAL,	-- Need OR
	nonCriticalExtension			SystemInformationBlockType2-v9e0-IEs	OPTIONAL
}

SystemInformationBlockType2-v9e0-IEs ::= SEQUENCE {
	ul-CarrierFreq-v9e0					ARFCN-ValueEUTRA-v9e0		OPTIONAL,	-- Cond ul-FreqMax
	nonCriticalExtension				SEQUENCE {}					OPTIONAL
}

AC-BarringConfig ::=				SEQUENCE {
	ac-BarringFactor					ENUMERATED {
											p00, p05, p10, p15, p20, p25, p30, p40,
											p50, p60, p70, p75, p80, p85, p90, p95},
	ac-BarringTime						ENUMERATED {s4, s8, s16, s32, s64, s128, s256, s512},
	ac-BarringForSpecialAC				BIT STRING (SIZE(5))
}

MBSFN-SubframeConfigList ::= 		SEQUENCE (SIZE (1..maxMBSFN-Allocations)) OF MBSFN-SubframeConfig

AC-BarringPerPLMN-List-r12 ::= 		SEQUENCE (SIZE (1.. maxPLMN-r11)) OF AC-BarringPerPLMN-r12

AC-BarringPerPLMN-r12 ::=			SEQUENCE {
	plmn-IdentityIndex-r12					INTEGER (1..maxPLMN-r11),
	ac-BarringInfo-r12						SEQUENCE {
		ac-BarringForEmergency-r12			BOOLEAN,
		ac-BarringForMO-Signalling-r12		AC-BarringConfig	OPTIONAL,	-- Need OP
		ac-BarringForMO-Data-r12			AC-BarringConfig	OPTIONAL	-- Need OP
	}															OPTIONAL,	-- Need OP
	ac-BarringSkipForMMTELVoice-r12		ENUMERATED {true}		OPTIONAL,	-- Need OP
	ac-BarringSkipForMMTELVideo-r12		ENUMERATED {true}		OPTIONAL,	-- Need OP
	ac-BarringSkipForSMS-r12			ENUMERATED {true}		OPTIONAL,	-- Need OP
	ac-BarringForCSFB-r12				AC-BarringConfig		OPTIONAL,	-- Need OP
	ssac-BarringForMMTEL-Voice-r12		AC-BarringConfig		OPTIONAL,	-- Need OP
	ssac-BarringForMMTEL-Video-r12		AC-BarringConfig		OPTIONAL	-- Need OP
}

ACDC-BarringForCommon-r13 ::=			SEQUENCE {
	acdc-HPLMNonly-r13					BOOLEAN,
	barringPerACDC-CategoryList-r13				BarringPerACDC-CategoryList-r13
}

ACDC-BarringPerPLMN-List-r13 ::= 		SEQUENCE (SIZE (1.. maxPLMN-r11)) OF ACDC-BarringPerPLMN-r13

ACDC-BarringPerPLMN-r13 ::=			SEQUENCE {
	plmn-IdentityIndex-r13				INTEGER (1..maxPLMN-r11),
	acdc-HPLMNonly-r13					BOOLEAN,
	barringPerACDC-CategoryList-r13				BarringPerACDC-CategoryList-r13
}

BarringPerACDC-CategoryList-r13 ::= SEQUENCE (SIZE (1..maxACDC-Cat-r13)) OF BarringPerACDC-Category-r13

BarringPerACDC-Category-r13 ::= SEQUENCE {
	acdc-CatValue-r13				INTEGER (1..maxACDC-Cat-r13),
	acdc-BarringConfig-r13			SEQUENCE {
		ac-BarringFactor-r13			ENUMERATED {
											p00, p05, p10, p15, p20, p25, p30, p40,
											p50, p60, p70, p75, p80, p85, p90, p95},
		ac-BarringTime-r13				ENUMERATED {s4, s8, s16, s32, s64, s128, s256, s512}
	}										OPTIONAL
}

-- ASN1STOP

SystemInformationBlockType2 field descriptions
ac-BarringFactor
If the random number drawn by the UE is lower than this value, access is allowed. Otherwise the access is barred. The values are interpreted in the range [0,1): p00 = 0, p05 = 0.05, p10 = 0.10,?, p95 = 0.95. Values other than p00 can only be set if all bits of the corresponding ac-BarringForSpecialAC are set to 0.
ac-BarringForCSFB
Access class barring for mobile originating CS fallback.
ac-BarringForEmergency
Access class barring for AC 10.
ac-BarringForMO-Data
Access class barring for mobile originating calls.
ac-BarringForMO-Signalling
Access class barring for mobile originating signalling.
ac-BarringForSpecialAC
Access class barring for AC 11-15. The first/ leftmost bit is for AC 11, the second bit is for AC 12, and so on.
ac-BarringTime
Mean access barring time value in seconds.
acdc-BarringConfig
Barring configuration for an ACDC category. If the field is absent, access to the cell is considered as not barred for the ACDC category in accordance with subclause 5.3.3.13.
acdc-CatValue
Indicates the ACDC category as defined in TS 24.105 [72].
acdc-HPLMNonly
Indicates whether ACDC is applicable for UEs not in their HPLMN for the corresponding PLMN. TRUE indicates that ACDC is applicable only for UEs in their HPLMN for the corresponding PLMN. FALSE indicates that ACDC is applicable for both UEs in their HPLMN and UEs not in their HPLMN for the corresponding PLMN.
additionalSpectrumEmission
The UE requirements related to IE AdditionalSpectrumEmission are defined in TS 36.101 [42, table 6.2.4.1].
barringPerACDC-CategoryList
A list of barring information per ACDC category according to the order defined in TS 22.011 [10]. The first entry in the list corresponds to the highest ACDC category of which applications are the least restricted in access attempts at a cell, the second entry in the list corresponds to the ACDC category of which applications are restricted more than applications of the highest ACDC category in access attempts at a cell, and so on. The last entry in the list corresponds to the lowest ACDC category of which applications are the most restricted in access attempts at a cell.
mbsfn-SubframeConfigList
Defines the subframes that are reserved for MBSFN in downlink.
multiBandInfoList
A list of additionalSpectrumEmission i.e. one for each additional frequency band included in multiBandInfoList in SystemInformationBlockType1, listed in the same order.
plmn-IdentityIndex
Index of the PLMN in plmn-IdentityList included in SIB1. Value 1 indicates the PLMN listed 1st in plmn-IdentityList included in SIB1. Value 2 indicates the PLMN listed 2nd in plmn-IdentityList included in SIB1 and so on.
ssac-BarringForMMTEL-Video
Service specific access class barring for MMTEL video originating calls.
ssac-BarringForMMTEL-Voice
Service specific access class barring for MMTEL voice originating calls.
ul-Bandwidth
Parameter: transmission bandwidth configuration, NRB, in uplink, see TS 36.101 [42, table 5.6-1]. Value n6 corresponds to 6 resource blocks, n15 to 15 resource blocks and so on. If for FDD this parameter is absent, the uplink bandwidth is equal to the downlink bandwidth. For TDD this parameter is absent and it is equal to the downlink bandwidth.
ul-CarrierFreq
For FDD: If absent, the (default) value determined from the default TX-RX frequency separation defined in TS 36.101 [42, table 5.7.3-1] applies.
For TDD: This parameter is absent and it is equal to the downlink frequency.
voiceServiceCauseIndication
Indicates whether UE is requested to use the establishment cause mo-VoiceCall for mobile originating MMTEL voice calls.

Conditional presence
Explanation
ul-FreqMax
The field is mandatory present if ul-CarrierFreq (i.e. without suffix) is present and set to maxEARFCN. Otherwise the field is not present.

-	SystemInformationBlockType3
The IE SystemInformationBlockType3 contains cell re-selection information common for intra-frequency, inter-frequency and/ or inter-RAT cell re-selection (i.e. applicable for more than one type of cell re-selection but not necessarily all) as well as intra-frequency cell re-selection information other than neighbouring cell related.
SystemInformationBlockType3 information element
-- ASN1START

SystemInformationBlockType3 ::=		SEQUENCE {
	cellReselectionInfoCommon			SEQUENCE {
		q-Hyst								ENUMERATED {
												dB0, dB1, dB2, dB3, dB4, dB5, dB6, dB8, dB10,
												dB12, dB14, dB16, dB18, dB20, dB22, dB24},
		speedStateReselectionPars			SEQUENCE {
			mobilityStateParameters				MobilityStateParameters,
			q-HystSF						SEQUENCE {
				sf-Medium						ENUMERATED {
														dB-6, dB-4, dB-2, dB0},
				sf-High							ENUMERATED {
														dB-6, dB-4, dB-2, dB0}
			}
		}																OPTIONAL		-- Need OP
	},
	cellReselectionServingFreqInfo		SEQUENCE {
		s-NonIntraSearch					ReselectionThreshold		OPTIONAL,		-- Need OP
		threshServingLow					ReselectionThreshold,
		cellReselectionPriority				CellReselectionPriority
	},
	intraFreqCellReselectionInfo		SEQUENCE {
		q-RxLevMin							Q-RxLevMin,
		p-Max								P-Max						OPTIONAL,		-- Need OP
		s-IntraSearch						ReselectionThreshold		OPTIONAL,		-- Need OP
		allowedMeasBandwidth				AllowedMeasBandwidth		OPTIONAL,		-- Need OP
		presenceAntennaPort1				PresenceAntennaPort1,
		neighCellConfig						NeighCellConfig,
		t-ReselectionEUTRA					T-Reselection,
		t-ReselectionEUTRA-SF				SpeedStateScaleFactors		OPTIONAL		-- Need OP
	},
	...,
	lateNonCriticalExtension				OCTET STRING (CONTAINING SystemInformationBlockType3-v10j0-IEs)	OPTIONAL,
	[[	s-IntraSearch-v920					SEQUENCE {
			s-IntraSearchP-r9					ReselectionThreshold,
			s-IntraSearchQ-r9					ReselectionThresholdQ-r9
		}																OPTIONAL,		-- Need OP
		s-NonIntraSearch-v920				SEQUENCE {
			s-NonIntraSearchP-r9				ReselectionThreshold,
			s-NonIntraSearchQ-r9				ReselectionThresholdQ-r9
		}																OPTIONAL,		-- Need OP
		q-QualMin-r9						Q-QualMin-r9				OPTIONAL,		-- Need OP
		threshServingLowQ-r9				ReselectionThresholdQ-r9	OPTIONAL		-- Need OP
	]],
	[[	q-QualMinWB-r11						Q-QualMin-r9				OPTIONAL	-- Cond WB-RSRQ
	]],
	[[	q-QualMinRSRQ-OnAllSymbols-r12			Q-QualMin-r9				OPTIONAL			-- Cond RSRQ
	]],
	[[	cellReselectionServingFreqInfo-v13xy CellReselectionServingFreqInfo-v13xy 	OPTIONAL,		-- Need OP
		redistributionServingInfo-r13			RedistributionServingInfo-r13 OPTIONAL	--Need OR
	]]
}

RedistributionServingInfo-r13 ::=		SEQUENCE {
	redistributionFactorServing-r13		INTEGER(0..10),
	redistributionFactorCell-r13		ENUMERATED{true}				OPTIONAL,	--Need OP
	t360-r13							ENUMERATED {min4, min8, min16, min32,infinity,
											spare3,spare2,spare1},
	redistrOnPagingOnly-r13				ENUMERATED {true}		OPTIONAL	--Need OP
}

CellReselectionServingFreqInfo-v13xy ::=	SEQUENCE {
	cellReselectionSubPriority-r13				CellReselectionSubPriority-r13
}

-- Late non critical extensions
SystemInformationBlockType3-v10j0-IEs ::= SEQUENCE {
	freqBandInfo-r10					NS-PmaxList-r10				OPTIONAL,	-- Need OR
	multiBandInfoList-v10j0				MultiBandInfoList-v10j0		OPTIONAL,	-- Need OR
	nonCriticalExtension				SEQUENCE {}					OPTIONAL
}

-- ASN1STOP

SystemInformationBlockType3 field descriptions
allowedMeasBandwidth
If absent, the value corresponding to the downlink bandwidth indicated by the dl-Bandwidth included in MasterInformationBlock applies.
cellReselectionInfoCommon
Cell re-selection information common for cells.
cellReselectionServingFreqInfo
Information common for Cell re-selection to inter-frequency and inter-RAT cells.
cellReselectionSubPriority
Fractional priority value added to cellReselectionPriority for the carrier.
freqBandInfo
A list of additionalPmax and additionalSpectrumEmission values as defined in TS 36.101 [42, table 6.2.4-1] applicable for the intra-frequency neighouring E-UTRA cells if the UE selects the frequenby band from freqBandIndicator in SystemInformationBlockType1.
intraFreqcellReselectionInfo
Cell re-selection information common for intra-frequency cells.
multiBandInfoList-v10j0
A list of additionalPmax and additionalSpectrumEmission values as defined in TS 36.101 [42, table 6.2.4-1] applicable for the intra-frequency neighouring E-UTRA cells if the UE selects the frequenby bands in multiBandInfoList (i.e. without suffix) or multiBandInfoList-v9e0. If E-UTRAN includes multiBandInfoList-v10j0, it includes the same number of entries, and listed in the same order, as in multiBandInfoList (i.e. without suffix).
p-Max
Value applicable for the intra-frequency neighbouring E-UTRA cells. If absent the UE applies the maximum power according to the UE capability.
redistrOnPagingOnly
If this field is present and the UE is redistribution capable, the UE shall only wait for the paging message to trigger E-UTRAN Inter-frequency Redistribution procedure as specified in 5.2.4.10 of 36.304[4].
q-Hyst
Parameter Qhyst in 36.304 [4], Value in dB. Value dB1 corresponds to 1 dB, dB2 corresponds to 2 dB and so on.
q-HystSF
Parameter "Speed dependent ScalingFactor for Qhyst" in TS 36.304 [4]. The sf-Medium and sf-High concern the additional hysteresis to be applied, in Medium and High Mobility state respectively, to Qhyst as defined in TS 36.304 [4]. In dB. Value dB-6 corresponds to -6dB, dB-4 corresponds to -4dB and so on.
q-QualMin
Parameter "Qqualmin" in TS 36.304 [4], applicable for intra-frequency neighrbour cells. If the field is not present, the UE applies the (default) value of negative infinity for Qqualmin. NOTE 1.
q-QualMinRSRQ-OnAllSymbols
If this field is present and supported by the UE, the UE shall, when performing RSRQ measurements, perform RSRQ measurement on all OFDM symbols in accordance with TS 36.214 [48]. NOTE 1.
q-QualMinWB
If this field is present and supported by the UE, the UE shall, when performing RSRQ measurements, use a wider bandwidth in accordance with TS 36.133 [16]. NOTE 1.
q-RxLevMin
Parameter "Qrxlevmin" in TS 36.304 [4], applicable for intra-frequency neighbour cells.
redistributionFactorCell
If redistributionFactorCell is present, this value is only applicable for the serving cell otherwise it is applicable for serving frequency
redistributionFactorServing
Parameter redistributionFactorServing in TS 36.304 [4].
s-IntraSearch
Parameter "SIntraSearchP" in TS 36.304 [4]. If the field s-IntraSearchP is present, the UE applies the value of s-IntraSearchP instead. Otherwise if neither s-IntraSearch nor s-IntraSearchP is present, the UE applies the (default) value of infinity for SIntraSearchP.
s-IntraSearchP
Parameter "SIntraSearchP" in TS 36.304 [4]. See descriptions under s-IntraSearch.
s-IntraSearchQ
Parameter "SIntraSearchQ" in TS 36.304 [4]. If the field is not present, the UE applies the (default) value of 0 dB for SIntraSearchQ.
s-NonIntraSearch
Parameter "SnonIntraSearchP" in TS 36.304 [4]. If the field s-NonIntraSearchP is present, the UE applies the value of s-NonIntraSearchP instead. Otherwise if neither s-NonIntraSearch nor s-NonIntraSearchP is present, the UE applies the (default) value of infinity for SnonIntraSearchP.
s-NonIntraSearchP
Parameter "SnonIntraSearchP" in TS 36.304 [4]. See descriptions under s-NonIntraSearch.
s-NonIntraSearchQ
Parameter "SnonIntraSearchQ" in TS 36.304 [4]. If the field is not present, the UE applies the (default) value of 0 dB for SnonIntraSearchQ.
speedStateReselectionPars
Speed dependent reselection parameters, see TS 36.304 [4]. If this field is absent, i.e, mobilityStateParameters is also not present, UE behaviour is specified in TS 36.304 [4].
t360
Parameter "T360" in TS 36.304 [4].
threshServingLow
Parameter "ThreshServing, LowP" in TS 36.304 [4].
threshServingLowQ
Parameter "ThreshServing, LowQ" in TS 36.304 [4].
t-ReselectionEUTRA
Parameter "TreselectionEUTRA" in TS 36.304 [4].
t-ReselectionEUTRA-SF
Parameter "Speed dependent ScalingFactor for TreselectionEUTRA" in TS 36.304 [4]. If the field is not present, the UE behaviour is specified in TS 36.304 [4].

NOTE 1:	The value the UE applies for parameter "Qqualmin" in TS 36.304 [4] depends on the q-QualMin fields signalled by E-UTRAN and supported by the UE. In case multiple candidate options are available, the UE shall select the highest priority candidate option according to the priority order indicated by the following table (top row is highest priority).
q-QualMinRSRQ-OnAllSymbols
q-QualMinWB
Value of parameter "Qqualmin" in TS 36.304 [4]
Included
Included
q-QualMinRSRQ-OnAllSymbols - (q-QualMin - q-QualMinWB)
Included
Not included
q-QualMinRSRQ-OnAllSymbols
Not included
Included
q-QualMinWB
Not included
Not included
q-QualMin

Conditional presence
Explanation
RSRQ
The field is optionally present, Need OR, if threshServingLowQ is present in SIB3; otherwise it is not present.
WB-RSRQ
The field is optionally present, need OP if the measurement bandwidth indicated by allowedMeasBandwidth is 50 resource blocks or larger; otherwise it is not present.

-	SystemInformationBlockType4
The IE SystemInformationBlockType4 contains neighbouring cell related information relevant only for intra-frequency cell re-selection. The IE includes cells with specific re-selection parameters as well as blacklisted cells.
SystemInformationBlockType4 information element
-- ASN1START

SystemInformationBlockType4 ::=		SEQUENCE {
	intraFreqNeighCellList				IntraFreqNeighCellList		OPTIONAL,	-- Need OR
	intraFreqBlackCellList				IntraFreqBlackCellList				OPTIONAL,	-- Need OR
	csg-PhysCellIdRange					PhysCellIdRange				OPTIONAL,	-- Cond CSG
	...,
	lateNonCriticalExtension				OCTET STRING				OPTIONAL
}

IntraFreqNeighCellList ::=		SEQUENCE (SIZE (1..maxCellIntra)) OF IntraFreqNeighCellInfo

IntraFreqNeighCellInfo ::=		SEQUENCE {
	physCellId								PhysCellId,
	q-OffsetCell							Q-OffsetRange,
	...
}

IntraFreqBlackCellList ::=		SEQUENCE (SIZE (1..maxCellBlack)) OF PhysCellIdRange

-- ASN1STOP

SystemInformationBlockType4 field descriptions
csg-PhysCellIdRange
Set of physical cell identities reserved for CSG cells on the frequency on which this field was received. The received csg-PhysCellIdRange applies if less than 24 hours has elapsed since it was received and the UE is camped on a cell of the same primary PLMN where this field was received. The 3 hour validity restriction (section 5.2.1.3) does not apply to this field. The UE shall not apply any stored csg-PhysCellIdRange when it is in any cell selection state defined in TS 36.304 [4].
intraFreqBlackCellList
List of blacklisted intra-frequency neighbouring cells.
intraFreqNeighbCellList
List of intra-frequency neighbouring cells with specific cell re-selection parameters.
q-OffsetCell
Parameter "Qoffsets,n" in TS 36.304 [4].

Conditional presence
Explanation
CSG
This field is optional, need OP, for non-CSG cells, and mandatory for CSG cells.

-	SystemInformationBlockType5
The IE SystemInformationBlockType5 contains information relevant only for inter-frequency cell re-selection i.e. information about other E-UTRA frequencies and inter-frequency neighbouring cells relevant for cell re-selection. The IE includes cell re-selection parameters common for a frequency as well as cell specific re-selection parameters.
SystemInformationBlockType5 information element
-- ASN1START

SystemInformationBlockType5 ::=		SEQUENCE {
	interFreqCarrierFreqList			InterFreqCarrierFreqList,
	...,
	lateNonCriticalExtension				OCTET STRING	(CONTAINING SystemInformationBlockType5-v8h0-IEs)				OPTIONAL,
	[[	interFreqCarrierFreqList-v1250	InterFreqCarrierFreqList-v1250		OPTIONAL,	-- Need OR
		interFreqCarrierFreqListExt-r12	InterFreqCarrierFreqListExt-r12 	OPTIONAL	-- Need OR
	]],
	[[	interFreqCarrierFreqListExt-v1280	InterFreqCarrierFreqListExt-v1280 	OPTIONAL	-- Need OR
	]],
	[[	interFreqCarrierFreqList-v13xy		InterFreqCarrierFreqList-v13xy		OPTIONAL,	-- Need OR
		interFreqCarrierFreqListExt-v13xy	InterFreqCarrierFreqListExt-v13xy 	OPTIONAL	-- Need OR
	]]
}

SystemInformationBlockType5-v8h0-IEs ::=	SEQUENCE {
	interFreqCarrierFreqList-v8h0 SEQUENCE (SIZE (1..maxFreq)) OF InterFreqCarrierFreqInfo-v8h0				 OPTIONAL,	-- Need OP
	nonCriticalExtension			SystemInformationBlockType5-v9e0-IEs							OPTIONAL
}

SystemInformationBlockType5-v9e0-IEs ::=	SEQUENCE {
	interFreqCarrierFreqList-v9e0	SEQUENCE (SIZE (1..maxFreq)) OF InterFreqCarrierFreqInfo-v9e0				OPTIONAL,	-- Need OR
	nonCriticalExtension			SystemInformationBlockType5-v10j0-IEs	OPTIONAL
}

SystemInformationBlockType5-v10j0-IEs ::=	SEQUENCE {
	interFreqCarrierFreqList-v10j0	SEQUENCE (SIZE (1..maxFreq)) OF InterFreqCarrierFreqInfo-v10j0				OPTIONAL,	-- Need OR
	nonCriticalExtension			SEQUENCE {}						OPTIONAL
}

InterFreqCarrierFreqList ::=		SEQUENCE (SIZE (1..maxFreq)) OF InterFreqCarrierFreqInfo

InterFreqCarrierFreqList-v1250 ::=	SEQUENCE (SIZE (1.. maxFreq)) OF InterFreqCarrierFreqInfo-v1250

InterFreqCarrierFreqListExt-r12 ::=	SEQUENCE (SIZE (1.. maxFreq)) OF InterFreqCarrierFreqInfo-r12

InterFreqCarrierFreqListExt-v1280 ::=	SEQUENCE (SIZE (1.. maxFreq)) OF InterFreqCarrierFreqInfo-v10j0

InterFreqCarrierFreqList-v13xy ::=	SEQUENCE (SIZE (1.. maxFreq)) OF InterFreqCarrierFreqInfo-v13xy

InterFreqCarrierFreqListExt-v13xy ::=	SEQUENCE (SIZE (1.. maxFreq)) OF InterFreqCarrierFreqInfo-v13xy

InterFreqCarrierFreqInfo ::=	SEQUENCE {
	dl-CarrierFreq						ARFCN-ValueEUTRA,
	q-RxLevMin							Q-RxLevMin,
	p-Max								P-Max							OPTIONAL,		-- Need OP
	t-ReselectionEUTRA					T-Reselection,
	t-ReselectionEUTRA-SF				SpeedStateScaleFactors			OPTIONAL,		-- Need OP
	threshX-High						ReselectionThreshold,
	threshX-Low							ReselectionThreshold,
	allowedMeasBandwidth				AllowedMeasBandwidth,
	presenceAntennaPort1				PresenceAntennaPort1,
	cellReselectionPriority				CellReselectionPriority			OPTIONAL,		-- Need OP
	neighCellConfig						NeighCellConfig,
	q-OffsetFreq						Q-OffsetRange					DEFAULT dB0,
	interFreqNeighCellList				InterFreqNeighCellList			OPTIONAL, 		-- Need OR
	interFreqBlackCellList				InterFreqBlackCellList			OPTIONAL, 		-- Need OR
	...,
	[[	q-QualMin-r9					Q-QualMin-r9					OPTIONAL,		-- Need OP
		threshX-Q-r9					SEQUENCE {
			threshX-HighQ-r9				ReselectionThresholdQ-r9,
			threshX-LowQ-r9					ReselectionThresholdQ-r9
		}																OPTIONAL		-- Cond RSRQ
	]],
	[[	q-QualMinWB-r11					Q-QualMin-r9					OPTIONAL	-- Cond WB-RSRQ
	]]
}

InterFreqCarrierFreqInfo-v8h0 ::=		SEQUENCE {
	multiBandInfoList					MultiBandInfoList				OPTIONAL	-- Need OR
}

InterFreqCarrierFreqInfo-v9e0 ::=	SEQUENCE {
	dl-CarrierFreq-v9e0					ARFCN-ValueEUTRA-v9e0	OPTIONAL,	-- Cond dl-FreqMax
	multiBandInfoList-v9e0				MultiBandInfoList-v9e0	OPTIONAL	-- Need OR
}

InterFreqCarrierFreqInfo-v10j0 ::=	SEQUENCE {
	freqBandInfo-r10					NS-PmaxList-r10				OPTIONAL,	-- Need OR
	multiBandInfoList-v10j0				MultiBandInfoList-v10j0		OPTIONAL	-- Need OR
}

InterFreqCarrierFreqInfo-v1250 ::=		SEQUENCE {
	reducedMeasPerformance-r12		ENUMERATED {true}		OPTIONAL,		-- Need OP
	q-QualMinRSRQ-OnAllSymbols-r12	Q-QualMin-r9					OPTIONAL	-- Cond RSRQ2
}

InterFreqCarrierFreqInfo-r12 ::=		SEQUENCE {
	dl-CarrierFreq-r12					ARFCN-ValueEUTRA-r9,
	q-RxLevMin-r12						Q-RxLevMin,
	p-Max-r12							P-Max							OPTIONAL,		-- Need OP
	t-ReselectionEUTRA-r12				T-Reselection,
	t-ReselectionEUTRA-SF-r12			SpeedStateScaleFactors			OPTIONAL,		-- Need OP
	threshX-High-r12					ReselectionThreshold,
	threshX-Low-r12						ReselectionThreshold,
	allowedMeasBandwidth-r12			AllowedMeasBandwidth,
	presenceAntennaPort1-r12			PresenceAntennaPort1,
	cellReselectionPriority-r12			CellReselectionPriority			OPTIONAL,		-- Need OP
	neighCellConfig-r12					NeighCellConfig,
	q-OffsetFreq-r12					Q-OffsetRange					DEFAULT dB0,
	interFreqNeighCellList-r12			InterFreqNeighCellList			OPTIONAL, 		-- Need OR
	interFreqBlackCellList-r12			InterFreqBlackCellList			OPTIONAL, 		-- Need OR
	q-QualMin-r12						Q-QualMin-r9					OPTIONAL,		-- Need OP
	threshX-Q-r12						SEQUENCE {
		threshX-HighQ-r12					ReselectionThresholdQ-r9,
		threshX-LowQ-r12					ReselectionThresholdQ-r9
	}																	OPTIONAL,	-- Cond RSRQ
	q-QualMinWB-r12						Q-QualMin-r9					OPTIONAL,	-- Cond WB-RSRQ
	multiBandInfoList-r12				MultiBandInfoList-r11			OPTIONAL,	-- Need OR
	reducedMeasPerformance-r12			ENUMERATED {true}				OPTIONAL,	-- Need OP
	q-QualMinRSRQ-OnAllSymbols-r12		Q-QualMin-r9					OPTIONAL,	-- Cond RSRQ2
...
}

InterFreqCarrierFreqInfo-v13xy	::=	SEQUENCE {
	cellReselectionSubPriority-r13		CellReselectionSubPriority-r13		OPTIONAL,		-- Need OP
	redistributionInterFreqInfo-r13		RedistributionInterFreqInfo-r13		OPTIONAL --Need OP
}

InterFreqNeighCellList ::=			SEQUENCE (SIZE (1..maxCellInter)) OF InterFreqNeighCellInfo

InterFreqNeighCellInfo ::=			SEQUENCE {
	physCellId							PhysCellId,
	q-OffsetCell						Q-OffsetRange
}

InterFreqBlackCellList ::=			SEQUENCE (SIZE (1..maxCellBlack)) OF PhysCellIdRange

RedistributionInterFreqInfo-r13 ::=		SEQUENCE {
	redistributionFactorFreq-r13			RedistributionFactor-r13	OPTIONAL,	--Need OP
	redistributionNeighCellList-r13			RedistributionNeighCellList-r13		OPTIONAL	--Need OP
}

RedistributionNeighCellList-r13 ::=		SEQUENCE (SIZE (1..maxCellInter)) OF RedistributionNeighCell-r13

RedistributionNeighCell-r13 ::=		SEQUENCE {
	physCellId										PhysCellId,
	redistributionFactorCell-r13					RedistributionFactor-r13
}

RedistributionFactor-r13 ::=	INTEGER(1..10)

-- ASN1STOP

SystemInformationBlockType5 field descriptions
cellReselectionSubPriority
Fractional priority value added to cellReselectionPriority for the carrier.
freqBandInfo
A list of additionalPmax and additionalSpectrumEmission values as defined in TS 36.101 [42, table 6.2.4-1] for the frequency band represented by dl-CarrierFreq for which cell reselection parameters are common.
interFreqBlackCellList
List of blacklisted inter-frequency neighbouring cells.
interFreqCarrierFreqList
List of neighbouring inter-frequencies. E-UTRAN does not configure more than one entry for the same physical frequency regardless of the E-ARFCN used to indicate this. If E-UTRAN includes interFreqCarrierFreqList-v8h0, interFreqCarrierFreqList-v9e0, InterFreqCarrierFreqList-v1250 and/or InterFreqCarrierFreqList-v13xy, it includes the same number of entries, and listed in the same order, as in interFreqCarrierFreqList (i.e. without suffix). See Annex D for more descriptions.
interFreqCarrierFreqListExt
List of additional neighbouring inter-frequencies, i.e. extending the size of the inter-frequency carrier list using the general principles specified in 5.1.2. E-UTRAN does not configure more than one entry for the same physical frequency regardless of the E-ARFCN used to indicate this. EUTRAN may include interFreqCarrierFreqListExt even if interFreqCarrierFreqList (i.e without suffix) does not include maxFreq entries. If E-UTRAN includes InterFreqCarrierFreqListExt-v13xy it includes the same number of entries, and listed in the same order, as in interFreqCarrierFreqListExt-r12.
interFreqNeighCellList
List of inter-frequency neighbouring cells with specific cell re-selection parameters.
multiBandInfoList
Indicates the list of frequency bands in addition to the band represented by dl-CarrierFreq for which cell reselection parameters are common. E-UTRAN indicates at most maxMultiBands frequency bands (i.e. the total number of entries across both multiBandInfoList and multiBandInfoList-v9e0 is below this limit).
multiBandInfoList-v10j0
A list of additionalPmax and additionalSpectrumEmission values as defined in TS 36.101 [42, table 6.2.4-1] for the frequency bands in multiBandInfoList (i.e. without suffix) and multiBandInfoList-v9e0. If E-UTRAN includes multiBandInfoList-v10j0, it includes the same number of entries, and listed in the same order, as in multiBandInfoList (i.e. without suffix).
p-Max
Value applicable for the neighbouring E-UTRA cells on this carrier frequency. If absent the UE applies the maximum power according to the UE capability.
q-OffsetCell
Parameter "Qoffsets,n" in TS 36.304 [4].
q-OffsetFreq
Parameter "Qoffsetfrequency" in TS 36.304 [4].
q-QualMin
Parameter "Qqualmin" in TS 36.304 [4]. If the field is not present, the UE applies the (default) value of negative infinity for Qqualmin. NOTE 1.
q-QualMinRSRQ-OnAllSymbols
If this field is present and supported by the UE, the UE shall, when performing RSRQ measurements, perform RSRQ measurement on all OFDM symbols in accordance with TS 36.214 [48]. NOTE 1.
q-QualMinWB
If this field is present and supported by the UE, the UE shall, when performing RSRQ measurements, use a wider bandwidth in accordance with TS 36.133 [16]. NOTE 1.
redistributionFactorFreq
Parameter redistributionFactorFreq in TS 36.304 [4].
redistributionFactorCell
Parameter redistributionFactorCell in TS 36.304 [4].
reducedMeasPerformance
Value TRUE indicates that the neighbouring inter-frequency is configured for reduced measurement performance, see TS 36.133 [16]. If the field is not included, the neighbouring inter-frequency is configured for normal measurement performance, see TS 36.133 [16]. 
threshX-High
Parameter "ThreshX, HighP" in TS 36.304 [4].
threshX-HighQ
Parameter "ThreshX, HighQ" in TS 36.304 [4].
threshX-Low
Parameter "ThreshX, LowP" in TS 36.304 [4].
threshX-LowQ
Parameter "ThreshX, LowQ" in TS 36.304 [4].
t-ReselectionEUTRA
Parameter "TreselectionEUTRA" in TS 36.304 [4].
t-ReselectionEUTRA-SF
Parameter "Speed dependent ScalingFactor for TreselectionEUTRA" in TS 36.304 [4]. If the field is not present, the UE behaviour is specified in TS 36.304 [4].

NOTE 1:	The value the UE applies for parameter "Qqualmin" in TS 36.304 [4] depends on the q-QualMin fields signalled by E-UTRAN and supported by the UE. In case multiple candidate options are available, the UE shall select the highest priority candidate option according to the priority order indicated by the following table (top row is highest priority).
q-QualMinRSRQ-OnAllSymbols
q-QualMinWB
Value of parameter "Qqualmin" in TS 36.304 [4]
Included
Included
q-QualMinRSRQ-OnAllSymbols - (q-QualMin - q-QualMinWB)
Included
Not included
q-QualMinRSRQ-OnAllSymbols
Not included
Included
q-QualMinWB
Not included
Not included
q-QualMin

Conditional presence
Explanation
dl-FreqMax
The field is mandatory present if, for the corresponding entry in InterFreqCarrierFreqList (i.e. without suffix), dl-CarrierFreq (i.e. without suffix) is set to maxEARFCN. Otherwise the field is not present.
RSRQ
The field is mandatory present if threshServingLowQ is present in systemInformationBlockType3; otherwise it is not present.
RSRQ2
The field is mandatory present for all EUTRA carriers listed in SIB5 if q-QualMinRSRQ-OnAllSymbols is present in SIB3; otherwise it is not present and the UE shall delete any existing value for this field.
WB-RSRQ
The field is optionally present, need OP if the measurement bandwidth indicated by allowedMeasBandwidth is 50 resource blocks or larger; otherwise it is not present.

-	SystemInformationBlockType6
The IE SystemInformationBlockType6 contains information relevant only for inter-RAT cell re-selection i.e. information about UTRA frequencies and UTRA neighbouring cells relevant for cell re-selection. The IE includes cell re-selection parameters common for a frequency.
SystemInformationBlockType6 information element
-- ASN1START

SystemInformationBlockType6 ::=		SEQUENCE {
	carrierFreqListUTRA-FDD				CarrierFreqListUTRA-FDD			OPTIONAL, 		-- Need OR
	carrierFreqListUTRA-TDD				CarrierFreqListUTRA-TDD			OPTIONAL, 		-- Need OR
	t-ReselectionUTRA					T-Reselection,
	t-ReselectionUTRA-SF				SpeedStateScaleFactors			OPTIONAL,		-- Need OP
	...,
	lateNonCriticalExtension			OCTET STRING	(CONTAINING SystemInformationBlockType6-v8h0-IEs)					OPTIONAL,
	[[	carrierFreqListUTRA-FDD-v1250 SEQUENCE (SIZE (1..maxUTRA-FDD-Carrier)) OF
										CarrierFreqInfoUTRA-v1250		OPTIONAL,	-- Cond UTRA-FDD
		carrierFreqListUTRA-TDD-v1250 SEQUENCE (SIZE (1..maxUTRA-TDD-Carrier)) OF
										CarrierFreqInfoUTRA-v1250		OPTIONAL,	-- Cond UTRA-TDD
		carrierFreqListUTRA-FDD-Ext-r12	CarrierFreqListUTRA-FDD-Ext-r12 OPTIONAL,	-- Cond UTRA-FDD
		carrierFreqListUTRA-TDD-Ext-r12 	CarrierFreqListUTRA-TDD-Ext-r12 OPTIONAL		-- Cond UTRA-TDD
	]]
}

SystemInformationBlockType6-v8h0-IEs ::=	SEQUENCE {
	carrierFreqListUTRA-FDD-v8h0 SEQUENCE (SIZE (1..maxUTRA-FDD-Carrier)) OF CarrierFreqInfoUTRA-FDD-v8h0 OPTIONAL,	-- Cond UTRA-FDD
	nonCriticalExtension			
SEQUENCE {}							OPTIONAL
}

CarrierFreqInfoUTRA-v1250 ::=		SEQUENCE {
	reducedMeasPerformance-r12		ENUMERATED {true}		OPTIONAL		-- Need OP
}

CarrierFreqListUTRA-FDD ::=		SEQUENCE (SIZE (1..maxUTRA-FDD-Carrier)) OF CarrierFreqUTRA-FDD 

CarrierFreqUTRA-FDD ::=				SEQUENCE {
	carrierFreq							ARFCN-ValueUTRA,
	cellReselectionPriority				CellReselectionPriority			OPTIONAL, 		-- Need OP
	threshX-High						ReselectionThreshold,
	threshX-Low							ReselectionThreshold,
	q-RxLevMin							INTEGER (-60..-13),
	p-MaxUTRA							INTEGER (-50..33),
	q-QualMin							INTEGER (-24..0),
	...,
	[[	threshX-Q-r9					SEQUENCE {
			threshX-HighQ-r9				ReselectionThresholdQ-r9,
			threshX-LowQ-r9					ReselectionThresholdQ-r9
		}																OPTIONAL		-- Cond RSRQ
	]]
}

CarrierFreqInfoUTRA-FDD-v8h0 ::=			SEQUENCE {
	multiBandInfoList					SEQUENCE (SIZE (1..maxMultiBands)) OF FreqBandIndicator-UTRA-FDD				OPTIONAL	-- Need OR
}

CarrierFreqListUTRA-FDD-Ext-r12 ::=	SEQUENCE (SIZE (1..maxUTRA-FDD-Carrier)) OF
									 CarrierFreqUTRA-FDD-Ext-r12

CarrierFreqUTRA-FDD-Ext-r12 ::= 				SEQUENCE {
	carrierFreq-r12						ARFCN-ValueUTRA,
	cellReselectionPriority-r12			CellReselectionPriority			OPTIONAL, 	-- Need OP
	threshX-High-r12					ReselectionThreshold,
	threshX-Low-r12						ReselectionThreshold,
	q-RxLevMin-r12						INTEGER (-60..-13),
	p-MaxUTRA-r12						INTEGER (-50..33),
	q-QualMin-r12						INTEGER (-24..0),
	threshX-Q-r12						SEQUENCE {
			threshX-HighQ-r12				ReselectionThresholdQ-r9,
			threshX-LowQ-r12				ReselectionThresholdQ-r9
	}																OPTIONAL,		-- Cond RSRQ
	multiBandInfoList-r12				SEQUENCE (SIZE (1..maxMultiBands)) OF FreqBandIndicator-UTRA-FDD				OPTIONAL,	-- Need OR
	reducedMeasPerformance-r12			ENUMERATED {true}				OPTIONAL,	-- Need OP
	...
}

CarrierFreqListUTRA-TDD ::=		SEQUENCE (SIZE (1..maxUTRA-TDD-Carrier)) OF CarrierFreqUTRA-TDD 

CarrierFreqUTRA-TDD ::=				SEQUENCE {
	carrierFreq							ARFCN-ValueUTRA,
	cellReselectionPriority				CellReselectionPriority			OPTIONAL, 		-- Need OP
	threshX-High						ReselectionThreshold,
	threshX-Low							ReselectionThreshold,
	q-RxLevMin							INTEGER (-60..-13),
	p-MaxUTRA							INTEGER (-50..33),
	...
}

CarrierFreqListUTRA-TDD-Ext-r12 ::=	SEQUENCE (SIZE (1..maxUTRA-TDD-Carrier)) OF
									 CarrierFreqUTRA-TDD-r12

CarrierFreqUTRA-TDD-r12 ::=	SEQUENCE {
	carrierFreq-r12						ARFCN-ValueUTRA,
	cellReselectionPriority-r12			CellReselectionPriority			OPTIONAL, 		-- Need OP
	threshX-High-r12					ReselectionThreshold,
	threshX-Low-r12						ReselectionThreshold,
	q-RxLevMin-r12						INTEGER (-60..-13),
	p-MaxUTRA-r12						INTEGER (-50..33),
	reducedMeasPerformance-r12			ENUMERATED {true}				OPTIONAL,	-- Need OP
	...
}

FreqBandIndicator-UTRA-FDD ::=				INTEGER (1..86)

-- ASN1STOP

SystemInformationBlockType6 field descriptions
carrierFreqListUTRA-FDD
List of carrier frequencies of UTRA FDD. E-UTRAN does not configure more than one entry for the same physical frequency regardless of the ARFCN used to indicate this. If E-UTRAN includes carrierFreqListUTRA-FDD-v8h0 and/or carrierFreqListUTRA-FDD-v1250, it includes the same number of entries, and listed in the same order, as in carrierFreqListUTRA-FDD (i.e. without suffix). See Annex D for more descriptions.
carrierFreqListUTRA-FDD-Ext
List of additional carrier frequencies of UTRA FDD. E-UTRAN does not configure more than one entry for the same physical frequency regardless of the ARFCN used to indicate this. EUTRAN may include carrierFreqListUTRA-FDD-Ext even if carrierFreqListUTRA-FDD (i.e without suffix) does not include maxUTRA-FDD-Carrier entries.
carrierFreqListUTRA-TDD
List of carrier frequencies of UTRA TDD. E-UTRAN does not configure more than one entry for the same physical frequency regardless of the ARFCN used to indicate this If E-UTRAN includes carrierFreqListUTRA-TDD-v1250, it includes the same number of entries, and listed in the same order, as in carrierFreqListUTRA-TDD (i.e. without suffix).
carrierFreqListUTRA-TDD-Ext
List of additional carrier frequencies of UTRA TDD. E-UTRAN does not configure more than one entry for the same physical frequency regardless of the ARFCN used to indicate this. EUTRAN may include carrierFreqListUTRA-TDD-Ext even if carrierFreqListUTRA-TDD (i.e without suffix) does not include maxUTRA-TDD-Carrier entries.
multiBandInfoList
Indicates the list of frequency bands in addition to the band represented by carrierFreq in the CarrierFreqUTRA-FDD for which UTRA cell reselection parameters are common.
p-MaxUTRA
The maximum allowed transmission power on the (uplink) carrier frequency, see TS 25.304 [40]. In dBm
q-QualMin
Parameter "Qqualmin" in TS 25.304 [40]. Actual value = IE value [dB].
q-RxLevMin
Parameter "Qrxlevmin" in TS 25.304 [40]. Actual value = IE value * 2+1 [dBm].
reducedMeasPerformance
Value TRUE indicates that the UTRA carrier frequency is configured for reduced measurement performance, see TS 36.133 [16]. If the field is not included, the UTRA carrier frequency is configured for normal measurement performance, see TS 36.133 [16].
t-ReselectionUTRA
Parameter "TreselectionUTRAN" in TS 36.304 [4].
t-ReselectionUTRA-SF
Parameter "Speed dependent ScalingFactor for TreselectionUTRA" in TS 36.304 [4]. If the field is not present, the UE behaviour is specified in TS 36.304 [4].
threshX-High
Parameter "ThreshX, HighP" in TS 36.304 [4].
threshX-HighQ
Parameter "ThreshX, HighQ" in TS 36.304 [4].
threshX-Low
 Parameter "ThreshX, LowP" in TS 36.304 [4].
threshX-LowQ
 Parameter "ThreshX, LowQ" in TS 36.304 [4].

Conditional presence
Explanation
RSRQ
The field is mandatory present if the threshServingLowQ is present in systemInformationBlockType3; otherwise it is not present.
UTRA-FDD
The field is optionally present, need OR, if the carrierFreqListUTRA-FDD is present. Otherwise it is not present.
UTRA-TDD
The field is optionally present, need OR, if the carrierFreqListUTRA-TDD is present. Otherwise it is not present.

-	SystemInformationBlockType7
The IE SystemInformationBlockType7 contains information relevant only for inter-RAT cell re-selection i.e. information about GERAN frequencies relevant for cell re-selection. The IE includes cell re-selection parameters for each frequency.
SystemInformationBlockType7 information element
-- ASN1START

SystemInformationBlockType7 ::=		SEQUENCE {
	t-ReselectionGERAN					T-Reselection,
	t-ReselectionGERAN-SF				SpeedStateScaleFactors				OPTIONAL,	-- Need OR
	carrierFreqsInfoList				CarrierFreqsInfoListGERAN			OPTIONAL,	-- Need OR
	...,
	lateNonCriticalExtension				OCTET STRING				OPTIONAL
}

CarrierFreqsInfoListGERAN ::=			SEQUENCE (SIZE (1..maxGNFG)) OF CarrierFreqsInfoGERAN

CarrierFreqsInfoGERAN ::=			SEQUENCE {
	carrierFreqs						CarrierFreqsGERAN,
	commonInfo							SEQUENCE {
		cellReselectionPriority				CellReselectionPriority			OPTIONAL,	-- Need OP
		ncc-Permitted						BIT STRING (SIZE (8)),
		q-RxLevMin							INTEGER (0..45),
		p-MaxGERAN							INTEGER (0..39)					OPTIONAL,	-- Need OP
		threshX-High						ReselectionThreshold,
		threshX-Low							ReselectionThreshold
	},
	...
}

-- ASN1STOP

SystemInformationBlockType7 field descriptions
carrierFreqs
The list of GERAN carrier frequencies organised into one group of GERAN carrier frequencies.
carrierFreqsInfoList
Provides a list of neighbouring GERAN carrier frequencies, which may be monitored for neighbouring GERAN cells. The GERAN carrier frequencies are organised in groups and the cell reselection parameters are provided per group of GERAN carrier frequencies.
commonInfo
Defines the set of cell reselection parameters for the group of GERAN carrier frequencies.
ncc-Permitted
Field encoded as a bit map, where bit N is set to "0" if a BCCH carrier with NCC = N-1 is not permitted for monitoring and set to "1" if the BCCH carrier with NCC = N-1 is permitted for monitoring; N = 1 to 8; bit 1 of the bitmap is the leading bit of the bit string.
p-MaxGERAN
Maximum allowed transmission power for GERAN on an uplink carrier frequency, see TS 45.008 [28]. Value in dBm. Applicable for the neighbouring GERAN cells on this carrier frequency. If pmaxGERAN is absent, the maximum power according to the UE capability is used.
q-RxLevMin
Parameter "Qrxlevmin" in TS 36.304 [1], minimum required RX level in the GSM cell. The actual value of Qrxlevmin in dBm = (IE value * 2) ? 115.
threshX-High
Parameter "ThreshX, HighP" in TS 36.304 [4].
threshX-Low
Parameter "ThreshX, LowP" in TS 36.304 [4].
t-ReselectionGERAN
Parameter "TreselectionGERAN" in TS 36.304 [4].
t-ReselectionGERAN-SF
Parameter "Speed dependent ScalingFactor for TreselectionGERAN" in TS 36.304 [4]. If the field is not present, the UE behaviour is specified in TS 36.304 [4].

-	SystemInformationBlockType8
The IE SystemInformationBlockType8 contains information relevant only for inter-RAT cell re-selection i.e. information about CDMA2000 frequencies and CDMA2000 neighbouring cells relevant for cell re-selection. The IE includes cell re-selection parameters common for a frequency as well as cell specific re-selection parameters.
SystemInformationBlockType8 information element
-- ASN1START

SystemInformationBlockType8 ::=		SEQUENCE {
	systemTimeInfo						SystemTimeInfoCDMA2000				OPTIONAL,	-- Need OR
	searchWindowSize					INTEGER (0..15)						OPTIONAL,	-- Need OR
	parametersHRPD						SEQUENCE {
		preRegistrationInfoHRPD				PreRegistrationInfoHRPD,
		cellReselectionParametersHRPD		CellReselectionParametersCDMA2000	OPTIONAL -- Need OR
	}																		OPTIONAL,	-- Need OR
	parameters1XRTT						SEQUENCE {
		csfb-RegistrationParam1XRTT			CSFB-RegistrationParam1XRTT		OPTIONAL,	-- Need OP
		longCodeState1XRTT					BIT STRING (SIZE (42))			OPTIONAL,	-- Need OR
		cellReselectionParameters1XRTT		CellReselectionParametersCDMA2000	OPTIONAL -- Need OR
	}																		OPTIONAL,	-- Need OR
	...,
	lateNonCriticalExtension			OCTET STRING						OPTIONAL,
	[[	csfb-SupportForDualRxUEs-r9			BOOLEAN							OPTIONAL,	-- Need OR
		cellReselectionParametersHRPD-v920	CellReselectionParametersCDMA2000-v920	OPTIONAL,	-- Cond NCL-HRPD
		cellReselectionParameters1XRTT-v920	CellReselectionParametersCDMA2000-v920	OPTIONAL,	-- Cond NCL-1XRTT
		csfb-RegistrationParam1XRTT-v920	CSFB-RegistrationParam1XRTT-v920		OPTIONAL,	-- Cond REG-1XRTT
		ac-BarringConfig1XRTT-r9			AC-BarringConfig1XRTT-r9	OPTIONAL	-- Cond REG-1XRTT
	]],
	[[	csfb-DualRxTxSupport-r10			ENUMERATED {true}			OPTIONAL	-- Cond REG-1XRTT
	]],
	[[	sib8-PerPLMN-List-r11				SIB8-PerPLMN-List-r11		OPTIONAL	-- Need OR
	]]
}

CellReselectionParametersCDMA2000 ::= SEQUENCE {
	bandClassList						BandClassListCDMA2000,
	neighCellList						NeighCellListCDMA2000,
	t-ReselectionCDMA2000			T-Reselection,
	t-ReselectionCDMA2000-SF			SpeedStateScaleFactors				OPTIONAL	-- Need OP
}

CellReselectionParametersCDMA2000-r11 ::= SEQUENCE {
	bandClassList						BandClassListCDMA2000,
	neighCellList-r11					SEQUENCE (SIZE (1..16)) OF NeighCellCDMA2000-r11,
	t-ReselectionCDMA2000				T-Reselection,
	t-ReselectionCDMA2000-SF			SpeedStateScaleFactors				OPTIONAL	-- Need OP
}

CellReselectionParametersCDMA2000-v920 ::= SEQUENCE {
	neighCellList-v920						NeighCellListCDMA2000-v920
}

NeighCellListCDMA2000 ::=			SEQUENCE (SIZE (1..16)) OF NeighCellCDMA2000

NeighCellCDMA2000 ::=	SEQUENCE {
	bandClass							BandclassCDMA2000,
	neighCellsPerFreqList				NeighCellsPerBandclassListCDMA2000
}

NeighCellCDMA2000-r11 ::=	SEQUENCE {
	bandClass							BandclassCDMA2000,
	neighFreqInfoList-r11				SEQUENCE (SIZE (1..16)) OF NeighCellsPerBandclassCDMA2000-r11
}

NeighCellsPerBandclassListCDMA2000 ::= SEQUENCE (SIZE (1..16)) OF NeighCellsPerBandclassCDMA2000

NeighCellsPerBandclassCDMA2000 ::=	SEQUENCE {
	arfcn								ARFCN-ValueCDMA2000,
	physCellIdList						PhysCellIdListCDMA2000
}

NeighCellsPerBandclassCDMA2000-r11 ::=	SEQUENCE {
	arfcn								ARFCN-ValueCDMA2000,
	physCellIdList-r11					SEQUENCE (SIZE (1..40)) OF PhysCellIdCDMA2000
}

NeighCellListCDMA2000-v920 ::=		SEQUENCE (SIZE (1..16)) OF NeighCellCDMA2000-v920

NeighCellCDMA2000-v920 ::=			SEQUENCE {
	neighCellsPerFreqList-v920			NeighCellsPerBandclassListCDMA2000-v920
}

NeighCellsPerBandclassListCDMA2000-v920 ::= SEQUENCE (SIZE (1..16)) OF NeighCellsPerBandclassCDMA2000-v920

NeighCellsPerBandclassCDMA2000-v920 ::=	SEQUENCE {
	physCellIdList-v920					PhysCellIdListCDMA2000-v920
}

PhysCellIdListCDMA2000 ::=			SEQUENCE (SIZE (1..16)) OF PhysCellIdCDMA2000

PhysCellIdListCDMA2000-v920 ::=		SEQUENCE (SIZE (0..24)) OF PhysCellIdCDMA2000

BandClassListCDMA2000 ::=			SEQUENCE (SIZE (1..maxCDMA-BandClass)) OF BandClassInfoCDMA2000

BandClassInfoCDMA2000 ::=	SEQUENCE {
	bandClass							BandclassCDMA2000,
	cellReselectionPriority				CellReselectionPriority				OPTIONAL,	-- Need OP
	threshX-High						INTEGER (0..63),
	threshX-Low							INTEGER (0..63),
	...
}

AC-BarringConfig1XRTT-r9 ::=		SEQUENCE {
	ac-Barring0to9-r9					INTEGER (0..63),
	ac-Barring10-r9						INTEGER (0..7),
	ac-Barring11-r9						INTEGER (0..7),
	ac-Barring12-r9						INTEGER (0..7),
	ac-Barring13-r9						INTEGER (0..7),
	ac-Barring14-r9						INTEGER (0..7),
	ac-Barring15-r9						INTEGER (0..7),
	ac-BarringMsg-r9					INTEGER (0..7),
	ac-BarringReg-r9					INTEGER (0..7),
	ac-BarringEmg-r9					INTEGER (0..7)
}

SIB8-PerPLMN-List-r11 ::=			SEQUENCE (SIZE (1..maxPLMN-r11)) OF SIB8-PerPLMN-r11

SIB8-PerPLMN-r11 ::=				SEQUENCE {
	plmn-Identity-r11					INTEGER (1..maxPLMN-r11),
	parametersCDMA2000-r11				CHOICE {
		explicitValue						ParametersCDMA2000-r11,
		defaultValue						NULL
	}
}

ParametersCDMA2000-r11 ::=			SEQUENCE {
	systemTimeInfo-r11					CHOICE	{
		explicitValue						SystemTimeInfoCDMA2000,
		defaultValue						NULL
	}																OPTIONAL,	-- Need OR
	searchWindowSize-r11				INTEGER (0..15),
	parametersHRPD-r11					SEQUENCE {
		preRegistrationInfoHRPD-r11			PreRegistrationInfoHRPD,
		cellReselectionParametersHRPD-r11	CellReselectionParametersCDMA2000-r11	OPTIONAL -- Need OR
	}		OPTIONAL,	-- Need OR
	parameters1XRTT-r11					SEQUENCE {
		csfb-RegistrationParam1XRTT-r11		CSFB-RegistrationParam1XRTT			OPTIONAL, -- Need OP
		csfb-RegistrationParam1XRTT-Ext-r11	CSFB-RegistrationParam1XRTT-v920	OPTIONAL, -- Cond REG-1XRTT-PerPLMN
		longCodeState1XRTT-r11				BIT STRING (SIZE (42))	OPTIONAL, -- Cond PerPLMN-LC
		cellReselectionParameters1XRTT-r11	CellReselectionParametersCDMA2000-r11	OPTIONAL, -- Need OR
		ac-BarringConfig1XRTT-r11			AC-BarringConfig1XRTT-r9			OPTIONAL, -- Cond REG-1XRTT-PerPLMN
		csfb-SupportForDualRxUEs-r11		BOOLEAN								OPTIONAL, -- Need OR
		csfb-DualRxTxSupport-r11			ENUMERATED {true}			OPTIONAL -- Cond REG-1XRTT-PerPLMN
	}		OPTIONAL,	-- Need OR
	...
}

-- ASN1STOP

SystemInformationBlockType8 field descriptions
ac-BarringConfig1XRTT
Contains the access class barring parameters the UE uses to calculate the access class barring factor, see C.S0097 [53].
ac-Barring0to9
Parameter used for calculating the access class barring factor for access overload classes 0 through 9. It is the parameter "PSIST" in C.S0004 [34] for access overload classes 0 through 9.
ac-BarringEmg
Parameter used for calculating the access class barring factor for emergency calls and emergency message transmissions for access overload classes 0 through 9. It is the parameter "PSIST_EMG" in C.S0004 [34].
ac-BarringMsg
Parameter used for modifying the access class barring factor for message transmissions. It is the parameter "MSG_PSIST" in C.S0004 [34].
ac-BarringN
Parameter used for calculating the access class barring factor for access overload class N (N = 10 to 15). It is the parameter "PSIST" in C.S0004 [34] for access overload class N.
ac-BarringReg
Parameter used for modifying the access class barring factor for autonomous registrations. It is the parameter "REG_PSIST" in C.S0004 [34].
bandClass
Identifies the Frequency Band in which the Carrier can be found. Details can be found in C.S0057 [24, Table 1.5].
bandClassList
List of CDMA2000 frequency bands.
cellReselectionParameters1XRTT
Cell reselection parameters applicable only to CDMA2000 1xRTT system.
cellReselectionParameters1XRTT-Ext
Cell reselection parameters applicable for cell reselection to CDMA2000 1XRTT system.
cellReselectionParameters1XRTT-v920
Cell reselection parameters applicable for cell reselection to CDMA2000 1XRTT system. The field is not present if cellReselectionParameters1XRTT is not present; otherwise it is optionally present.
cellReselectionParametersHRPD
Cell reselection parameters applicable for cell reselection to CDMA2000 HRPD system
cellReselectionParametersHRPD-Ext
Cell reselection parameters applicable for cell reselection to CDMA2000 HRPD system.
cellReselectionParametersHRPD-v920
Cell reselection parameters applicable for cell reselection to CDMA2000 HRPD system. The field is not present if cellReselectionParametersHRPD is not present; otherwise it is optionally present.
csfb-DualRxTxSupport
Value TRUE indicates that the network supports dual Rx/Tx enhanced 1xCSFB, which enables UEs capable of dual Rx/Tx enhanced 1xCSFB to switch off their 1xRTT receiver/transmitter while camped in E-UTRAN [51].
csfb-RegistrationParam1XRTT
Contains the parameters the UE will use to determine if it should perform a CDMA2000 1xRTT Registration/Re-Registration. This field is included if either CSFB or enhanced CS fallback to CDMA2000 1xRTT is supported.
csfb-SupportForDualRxUEs
Value TRUE indicates that the network supports dual Rx CSFB [51].
longCodeState1XRTT
The state of long code generation registers in CDMA2000 1XRTT system as defined in C.S0002 [12, Section 1.3] at ms, where t equals to the cdma-SystemTime. This field is required for 1xRTT Inter-RAT ANR, SRVCC handover and enhanced CS fallback to CDMA2000 1xRTT operation. Otherwise this IE is not needed. This field is excluded when estimating changes in system information, i.e. changes of longCodeState1XRTT should neither result in system information change notifications nor in a modification of systemInfoValueTag in SIB1.
neighCellList
List of CDMA2000 neighbouring cells. The total number of neighbouring cells in neighCellList for each RAT (1XRTT or HRPD) is limited to 32.
neighCellList-v920
Extended List of CDMA2000 neighbouring cells. The combined total number of CDMA2000 neighbouring cells in both neighCellList and neighCellList-v920 is limited to 32 for HRPD and 40 for 1xRTT.
neighCellsPerFreqList
List of carrier frequencies and neighbour cell ids in each frequency within a CDMA2000 Band, see C.S0002 [12] or C.S0024 [26].
neighCellsPerFreqList-v920
Extended list of neighbour cell ids, in the same CDMA2000 Frequency Band as the corresponding instance in "NeighCellListCDMA2000".
parameters1XRTT
Parameters applicable for interworking with CDMA2000 1XRTT system.
parametersCDMA2000
Provides the corresponding SIB8 parameters for the CDMA2000 network associated with the PLMN indicated in plmn-Identity. A choice is used to indicate whether for this PLMN the parameters are signalled explicitly or set to the (default) values common for all PLMNs i.e. the values not included in sib8-PerPLMN-List.
parametersHRPD
Parameters applicable only for interworking with CDMA2000 HRPD systems.
physCellIdList
Identifies the list of CDMA2000 cell ids, see C.S0002 [12] or C.S0024 [26].
physCellIdList-v920
Extended list of CDMA2000 cell ids, in the same CDMA2000 ARFCN as the corresponding instance in "NeighCellsPerBandclassCDMA2000".
plmn-Identity
Indicates the PLMN associated with this CDMA2000 network. Value 1 indicates the PLMN listed 1st in plmn-IdentityList included in SIB1, value 2 indicates the PLMN listed 2nd in plmn-IdentityList included in SIB1 and so on. A PLMN which identity is not indicated in the sib8-PerPLMN-List, does not support inter-working with CDMA2000.
preRegistrationInfoHRPD
The CDMA2000 HRPD Pre-Registration Information tells the UE if it should pre-register with the CDMA2000 HRPD network and identifies the Pre-registration zone to the UE.
searchWindowSize
The search window size is a CDMA2000 parameter to be used to assist in searching for the neighbouring pilots. For values see C.S0005 [25, Table 2.6.6.2.1-1] and C.S0024 [26, Table 8.7.6.2-4]. This field is required for a UE with rx-ConfigHRPD= single and/ or rx-Config1XRTT= single to perform handover, cell re-selection, UE measurement based redirection and enhanced 1xRTT CS fallback from E-UTRAN to CDMA2000 according to this specification and TS 36.304 [4].
sib8-PerPLMN-List
This field provides the values for the interworking CDMA2000 networks corresponding, if any, to the UE's RPLMN.
systemTimeInfo
Information on CDMA2000 system time. This field is required for a UE with rx-ConfigHRPD= single and/ or rx-Config1XRTT= single to perform handover, cell re-selection, UE measurement based redirection and enhanced 1xRTT CS fallback from E-UTRAN to CDMA2000 according to this specification and TS 36.304 [4]. This field is excluded when estimating changes in system information, i.e. changes of systemTimeInfo should neither result in system information change notifications nor in a modification of systemInfoValueTag in SIB1.
For the field included in ParametersCDMA2000, a choice is used to indicate whether for this PLMN the parameters are signalled explicitly or set to the (default) value common for all PLMNs i.e. the value not included in sib8-PerPLMN-List.
threshX-High
Parameter "ThreshX, HighP" in TS 36.304 [4]. This specifies the high threshold used in reselection towards this CDMA2000 band class expressed as an unsigned binary number equal to FLOOR (-2 x 10 x log10 Ec/Io) in units of 0.5 dB, as defined in C.S0005 [25].
threshX-Low
Parameter "ThreshX, LowP" in TS 36.304 [4]. This specifies the low threshold used in reselection towards this CDMA2000 band class expressed as an unsigned binary number equal to FLOOR (-2 x 10 x log10 Ec/Io) in units of 0.5 dB, as defined in C.S0005 [25].
t-ReselectionCDMA2000
Parameter "TreselectionCDMA_HRPD" or "TreselectionCDMA_1xRTT" in TS 36.304 [4].
t-ReselectionCDMA2000-SF
Parameter "Speed dependent ScalingFactor for TreselectionCDMA-HRPD" or TreselectionCDMA-1xRTT" in TS 36.304 [4]. If the field is not present, the UE behaviour is specified in TS 36.304 [4].

Conditional presence
Explanation
NCL-1XRTT
The field is optional present, need OR, if cellReselectionParameters1xRTT is present; otherwise it is not present.
NCL-HRPD
The field is optional present, need OR, if cellReselectionParametersHRPD is present; otherwise it is not present.
PerPLMN-LC
The field is optional present, need OR, when systemTimeInfo is included in SIB8PerPLMN for this CDMA2000 network; otherwise it is not present.
REG-1XRTT
The field is optional present, need OR, if csfb-RegistrationParam1XRTT is present; otherwise it is not present.
REG-1XRTT-PerPLMN
The field is optional present, need OR, if csfb-RegistrationParam1XRTT is included in SIB8PerPLMN for this CDMA2000 network; otherwise it is not present.

-	SystemInformationBlockType9
The IE SystemInformationBlockType9 contains a home eNB name (HNB Name).
SystemInformationBlockType9 information element
-- ASN1START

SystemInformationBlockType9 ::=		SEQUENCE {
	hnb-Name							OCTET STRING (SIZE(1..48))		OPTIONAL,	-- Need OR
	...,
	lateNonCriticalExtension				OCTET STRING				OPTIONAL
}

-- ASN1STOP

SystemInformationBlockType9 field descriptions
hnb-Name
Carries the name of the home eNB, coded in UTF-8 with variable number of bytes per character, see TS 22.011 [10].

-	SystemInformationBlockType10
The IE SystemInformationBlockType10 contains an ETWS primary notification.
SystemInformationBlockType10 information element
-- ASN1START

SystemInformationBlockType10 ::=	SEQUENCE {
	messageIdentifier					BIT STRING (SIZE (16)),
	serialNumber						BIT STRING (SIZE (16)),
	warningType							OCTET STRING (SIZE (2)),
	dummy								OCTET STRING (SIZE (50))	OPTIONAL,		-- Need OP
	...,
	lateNonCriticalExtension			OCTET STRING				OPTIONAL
}

-- ASN1STOP

SystemInformationBlockType10 field descriptions
messageIdentifier
Identifies the source and type of ETWS notification. The leading bit (which is equivalent to the leading bit of the equivalent IE defined in TS 36.413 [39, 9.2.1.44]) contains bit 7 of the first octet of the equivalent IE, defined in and encoded according to TS 23.041 [37, 9.4.3.2.1], while the trailing bit contains bit 0 of the second octet of the same equivalent IE.
serialNumber
Identifies variations of an ETWS notification. The leading bit (which is equivalent to the leading bit of the equivalent IE defined in TS 36.413 [39, 9.2.1.45]) contains bit 7 of the first octet of the equivalent IE, defined in and encoded according to TS 23.041 [37, 9.4.3.2.2], while the trailing bit contains bit 0 of the second octet of the same equivalent IE.
dummy
This field is not used in the specification. If received it shall be ignored by the UE.
warningType
Identifies the warning type of the ETWS primary notification and provides information on emergency user alert and UE popup. The first octet (which is equivalent to the first octet of the equivalent IE defined in TS 36.413 [39, 9.2.1.50]) contains the first octet of the equivalent IE defined in and encoded according to TS 23.041 [37, 9.3.24], and so on.

-	SystemInformationBlockType11
The IE SystemInformationBlockType11 contains an ETWS secondary notification.
SystemInformationBlockType11 information element
-- ASN1START

SystemInformationBlockType11 ::=	SEQUENCE {
	messageIdentifier					BIT STRING (SIZE (16)),
	serialNumber						BIT STRING (SIZE (16)),
	warningMessageSegmentType			ENUMERATED {notLastSegment, lastSegment},
	warningMessageSegmentNumber			INTEGER (0..63),
	warningMessageSegment				OCTET STRING,
	dataCodingScheme					OCTET STRING (SIZE (1)) 		OPTIONAL, 	-- Cond Segment1
	...,
	lateNonCriticalExtension				OCTET STRING				OPTIONAL
}

-- ASN1STOP

SystemInformationBlockType11 field descriptions
dataCodingScheme
Identifies the alphabet/coding and the language applied variations of an ETWS notification. The octet (which is equivalent to the octet of the equivalent IE defined in TS 36.413 [39, 9.2.1.52]) contains the octet of the equivalent IE defined in TS 23.041 [37, 9.4.3.2.3] and encoded according to TS 23.038 [38].
messageIdentifier
Identifies the source and type of ETWS notification. The leading bit (which is equivalent to the leading bit of the equivalent IE defined in TS 36.413 [39, 9.2.1.44]) contains bit 7 of the first octet of the equivalent IE, defined in and encoded according to TS 23.041 [37, 9.4.3.2.1], while the trailing bit contains bit 0 of second octet of the same equivalent IE.
serialNumber
Identifies variations of an ETWS notification. The leading bit (which is equivalent to the leading bit of the equivalent IE defined in TS 36.413 [39, 9.2.1.45]) contains bit 7 of the first octet of the equivalent IE, defined in and encoded according to TS 23.041 [37, 9.4.3.2.2], while the trailing bit contains bit 0 of second octet of the same equivalent IE.
warningMessageSegment
Carries a segment of the Warning Message Contents IE defined in TS 36.413 [39, 9.2.1.53]. The first octet of the Warning Message Contents IE is equivalent to the first octet of the CB data IE defined in and encoded according to TS 23.041 [37, 9.4.2.2.5] and so on.
warningMessageSegmentNumber
Segment number of the ETWS warning message segment contained in the SIB. A segment number of zero corresponds to the first segment, one corresponds to the second segment, and so on.
warningMessageSegmentType
Indicates whether the included ETWS warning message segment is the last segment or not.

Conditional presence
Explanation
Segment1
The field is mandatory present in the first segment of SIB11, otherwise it is not present.

-	SystemInformationBlockType12
The IE SystemInformationBlockType12 contains a CMAS notification.
SystemInformationBlockType12 information element
-- ASN1START

SystemInformationBlockType12-r9 ::=	SEQUENCE {
	messageIdentifier-r9				BIT STRING (SIZE (16)),
	serialNumber-r9						BIT STRING (SIZE (16)),
	warningMessageSegmentType-r9		ENUMERATED {notLastSegment, lastSegment},
	warningMessageSegmentNumber-r9		INTEGER (0..63),
	warningMessageSegment-r9			OCTET STRING,
	dataCodingScheme-r9					OCTET STRING (SIZE (1)) 		OPTIONAL, 	-- Cond Segment1
	lateNonCriticalExtension			OCTET STRING					OPTIONAL,
	...
}

-- ASN1STOP

SystemInformationBlockType12 field descriptions
dataCodingScheme
Identifies the alphabet/coding and the language applied variations of a CMAS notification. The octet (which is equivalent to the octet of the equivalent IE defined in TS 36.413 [39, 9.2.1.52]) contains the octet of the equivalent IE defined in TS 23.041 [37, 9.4.3.2.3] and encoded according to TS 23.038 [38].
messageIdentifier
Identifies the source and type of CMAS notification. The leading bit (which is equivalent to the leading bit of the equivalent IE defined in TS 36.413 [39, 9.2.1.44]) contains bit 7 of the first octet of the equivalent IE, defined in and encoded according to TS 23.041 [37, 9.4.3.2.1], while the trailing bit contains bit 0 of second octet of the same equivalent IE.
serialNumber
Identifies variations of a CMAS notification. The leading bit (which is equivalent to the leading bit of the equivalent IE defined in TS 36.413 [39, 9.2.1.45]) contains bit 7 of the first octet of the equivalent IE, defined in and encoded according to TS 23.041 [37, 9.4.3.2.2], while the trailing bit contains bit 0 of second octet of the same equivalent IE.
warningMessageSegment
Carries a segment of the Warning Message Contents IE defined in TS 36.413 [39]. The first octet of the Warning Message Contents IE is equivalent to the first octet of the CB data IE defined in and encoded according to TS 23.041 [37, 9.4.2.2.5] and so on.
warningMessageSegmentNumber
Segment number of the CMAS warning message segment contained in the SIB. A segment number of zero corresponds to the first segment, one corresponds to the second segment, and so on.
warningMessageSegmentType
Indicates whether the included CMAS warning message segment is the last segment or not.

Conditional presence
Explanation
Segment1
The field is mandatory present in the first segment of SIB12, otherwise it is not present.

-	SystemInformationBlockType13
The IE SystemInformationBlockType13 contains the information required to acquire the MBMS control information associated with one or more MBSFN areas.
SystemInformationBlockType13 information element
-- ASN1START

SystemInformationBlockType13-r9 ::=	SEQUENCE {
	mbsfn-AreaInfoList-r9				MBSFN-AreaInfoList-r9,
	notificationConfig-r9				MBMS-NotificationConfig-r9,
	lateNonCriticalExtension			OCTET STRING					OPTIONAL,
	...
}

-- ASN1STOP

SystemInformationBlockType13 field descriptions
notificationConfig
Indicates the MBMS notification related configuration parameters. The UE shall ignore this field when dl-Bandwidth included in MasterInformationBlock is set to n6.

-	SystemInformationBlockType14
The IE SystemInformationBlockType14 contains the EAB parameters.
SystemInformationBlockType14 information element
-- ASN1START

SystemInformationBlockType14-r11 ::=	SEQUENCE {
	eab-Param-r11							CHOICE {
		eab-Common-r11							EAB-Config-r11,
		eab-PerPLMN-List-r11					SEQUENCE (SIZE (1..maxPLMN-r11)) OF EAB-ConfigPLMN-r11
	}														OPTIONAL, -- Need OR
	lateNonCriticalExtension				OCTET STRING			OPTIONAL,
	...
}

EAB-ConfigPLMN-r11 ::=				SEQUENCE {
	eab-Config-r11						EAB-Config-r11				OPTIONAL -- Need OR
}

EAB-Config-r11 ::=					SEQUENCE {
	eab-Category-r11					ENUMERATED {a, b, c},
	eab-BarringBitmap-r11				BIT STRING (SIZE (10))
}

-- ASN1STOP

SystemInformationBlockType14 field descriptions
eab-BarringBitmap
Extended access class barring for AC 0-9. The first/ leftmost bit is for AC 0, the second bit is for AC 1, and so on.
eab-Category
Indicates the category of UEs for which EAB applies. Value a corresponds to all UEs, value b corresponds to the UEs that are neither in their HPLMN nor in a PLMN that is equivalent to it, and value c corresponds to the UEs that are neither in the PLMN listed as most preferred PLMN of the country where the UEs are roaming in the operator-defined PLMN selector list on the USIM, nor in their HPLMN nor in a PLMN that is equivalent to their HPLMN, see TS 22.011 [10].
eab-Common
The EAB parameters applicable for all PLMN(s).
eab-PerPLMN-List
The EAB parameters per PLMN, listed in the same order as the PLMN(s) occur in plmn-IdentityList in SystemInformationBlockType1.

-	SystemInformationBlockType15
The IE SystemInformationBlockType15 contains the MBMS Service Area Identities (SAI) of the current and/ or neighbouring carrier frequencies.
SystemInformationBlockType15 information element
-- ASN1START

SystemInformationBlockType15-r11 ::=	SEQUENCE {
	mbms-SAI-IntraFreq-r11					MBMS-SAI-List-r11				OPTIONAL,	-- Need OR
	mbms-SAI-InterFreqList-r11				MBMS-SAI-InterFreqList-r11		OPTIONAL,	-- Need OR
	lateNonCriticalExtension				OCTET STRING					OPTIONAL,
	...,
	[[	mbms-SAI-InterFreqList-v1140		MBMS-SAI-InterFreqList-v1140	OPTIONAL	-- Cond InterFreq
	]]
}

MBMS-SAI-List-r11 ::=					SEQUENCE (SIZE (1..maxSAI-MBMS-r11)) OF MBMS-SAI-r11

MBMS-SAI-r11 ::=						INTEGER (0..65535)

MBMS-SAI-InterFreqList-r11 ::=			SEQUENCE (SIZE (1..maxFreq)) OF MBMS-SAI-InterFreq-r11

MBMS-SAI-InterFreqList-v1140 ::=		SEQUENCE (SIZE (1..maxFreq)) OF MBMS-SAI-InterFreq-v1140

MBMS-SAI-InterFreq-r11 ::=				SEQUENCE {
	dl-CarrierFreq-r11						ARFCN-ValueEUTRA-r9,
	mbms-SAI-List-r11						MBMS-SAI-List-r11
}

MBMS-SAI-InterFreq-v1140 ::=			SEQUENCE {
		multiBandInfoList-r11				MultiBandInfoList-r11			OPTIONAL	-- Need OR
}


-- ASN1STOP

SystemInformationBlockType15 field descriptions
mbms-SAI-InterFreqList
Contains a list of neighboring frequencies including additional bands, if any, that provide MBMS services and the corresponding MBMS SAIs.
mbms-SAI-IntraFreq
Contains the list of MBMS SAIs for the current frequency. A duplicate MBMS SAI indicates that this and all following SAIs are not offered by this cell but only by neighbour cells on the current frequency. For MBMS service continuity, the UE shall use all MBMS SAIs listed in mbms-SAI-IntraFreq to derive the MBMS frequencies of interest.
mbms-SAI-List
Contains a list of MBMS SAIs for a specific frequency.
multiBandInfoList
A list of additional frequency bands applicable for the cells participating in the MBSFN transmission.

Conditional presence
Explanation
InterFreq
The field is optionally present, need OR, if the mbms-SAI-InterFreqList-r11 is present. Otherwise it is not present.

-	SystemInformationBlockType16
The IE SystemInformationBlockType16 contains information related to GPS time and Coordinated Universal Time (UTC). The UE may use the parameters provided in this system information block to obtain the UTC, the GPS and the local time.
NOTE:	The UE may use the time information for numerous purposes, possibly involving upper layers e.g. to assist GPS initialisation, to synchronise the UE clock (a.o. to determine MBMS session start/ stop).
SystemInformationBlockType16 information element
-- ASN1START

SystemInformationBlockType16-r11 ::=		SEQUENCE {
	timeInfo-r11							SEQUENCE {
		timeInfoUTC-r11						INTEGER (0..549755813887),
		dayLightSavingTime-r11				BIT STRING (SIZE (2))		OPTIONAL,	-- Need OR
		leapSeconds-r11						INTEGER (-127..128)			OPTIONAL,	-- Need OR
		localTimeOffset-r11					INTEGER (-63..64)			OPTIONAL	-- Need OR
	}																	OPTIONAL,	-- Need OR
	lateNonCriticalExtension			OCTET STRING				OPTIONAL,
	...
}

-- ASN1STOP

SystemInformationBlockType16 field descriptions
dayLightSavingTime
It indicates if and how daylight saving time (DST) is applied to obtain the local time. The semantics is the same as the semantics of the Daylight Saving Time IE in TS 24.301 [35] and TS 24.008 [49]. The first/leftmost bit of the bit string contains the b2 of octet 3, i.e. the value part of the Daylight Saving Time IE, and the second bit of the bit string contains b1 of octet 3.
leapSeconds
Number of leap seconds offset between GPS Time and UTC. UTC and GPS time are related i.e. GPS time -leapSeconds = UTC time.
localTimeOffset
Offset between UTC and local time in units of 15 minutes. Actual value = IE value * 15 minutes. Local time of the day is calculated as UTC time + localTimeOffset.
timeInfoUTC
Coordinated Universal Time corresponding to the SFN boundary at or immediately after the ending boundary of the SI-window in which SystemInformationBlockType16 is transmitted. The field counts the number of UTC seconds in 10 ms units since 00:00:00 on Gregorian calendar date 1 January, 1900 (midnight between Sunday, December 31, 1899 and Monday, January 1, 1900), including leap seconds and other additions prior to 1972. NOTE 1.
This field is excluded when estimating changes in system information, i.e. changes of timeInfoUTC should neither result in system information change notifications nor in a modification of systemInfoValueTag in SIB1.

NOTE 1:	For the sake of the field definition, it is assumed UTC existed prior to 1 January 1972. As this field counts total elapsed time, conversion to calendar UTC time needs to allow for leap second and other calendar adjustments since 1 January 1900. For example, time 00:00 on 1 January 1972 UTC corresponds to a timeInfoUTC of 2,272,060,800 seconds.
-	SystemInformationBlockType17
The IE SystemInformationBlockType17 contains information relevant for traffic steering between E-UTRAN and WLAN. 
SystemInformationBlockType17 information element
-- ASN1START

SystemInformationBlockType17-r12 ::=	SEQUENCE {
	wlan-OffloadInfoPerPLMN-List-r12		SEQUENCE (SIZE (1..maxPLMN-r11)) OF
										 WLAN-OffloadInfoPerPLMN-r12			OPTIONAL, -- Need OR
	lateNonCriticalExtension				OCTET STRING				OPTIONAL,
	...
}

WLAN-OffloadInfoPerPLMN-r12 ::= 			SEQUENCE {
	 	wlan-OffloadConfigCommon-r12		WLAN-OffloadConfig-r12		OPTIONAL, 	-- Need OR
		wlan-Id-List-r12					WLAN-Id-List-r12			OPTIONAL,	-- Need OR
		...
}

WLAN-Id-List-r12 ::=				SEQUENCE (SIZE (1..maxWLAN-Id-r12)) OF WLAN-Identifiers-r12

WLAN-Identifiers-r12 ::=			SEQUENCE {
	ssid-r12						OCTET STRING (SIZE (1..32))		OPTIONAL, 	-- Need OR
	bssid-r12						OCTET STRING (SIZE (6)) 			OPTIONAL, 	-- Need OR
	hessid-r12						OCTET STRING (SIZE (6)) 			OPTIONAL, 	-- Need OR
	...
}

-- ASN1STOP

SystemInformationBlockType17 field descriptions
bssid
Basic Service Set Identifier (BSSID) defined in IEEE 802.11-2012 [67].
hessid
Homogenous Extended Service Set Identifier (HESSID) defined in IEEE 802.11-2012 [67].
ssid
Service Set Identifier (SSID) defined in IEEE 802.11-2012 [67].
wlan-OffloadInfoPerPLMN-List
The WLAN offload configuration per PLMN includes the same number of entries, listed in the same order as the PLMN(s) in plmn-IdentityList in SystemInformationBlockType1.

-	SystemInformationBlockType18
The IE SystemInformationBlockType18 indicates E-UTRAN supports the Sidelink UE information procedure and may contain sidelink communication related resource configuration information.
SystemInformationBlockType18 information element
-- ASN1START

SystemInformationBlockType18-r12 ::= SEQUENCE {
	commConfig-r12						SEQUENCE {
		commRxPool-r12						SL-CommRxPoolList-r12,
		commTxPoolNormalCommon-r12			SL-CommTxPoolList-r12			OPTIONAL,	-- Need OR
		commTxPoolExceptional-r12			SL-CommTxPoolList-r12			OPTIONAL,	-- Need OR
		commSyncConfig-r12					SL-SyncConfigList-r12		OPTIONAL	-- Need OR
	}																		OPTIONAL,	-- Need OR
	lateNonCriticalExtension			OCTET STRING						OPTIONAL,
	...,
	[[	commTxPoolNormalCommonExt-r13			SL-CommTxPoolListExt-r13	OPTIONAL,	-- Need OR
		commTxAllowRelayCommon-r13				ENUMERATED {true}			OPTIONAL	-- Need OR
	]]
}

-- ASN1STOP

SystemInformationBlockType18 field descriptions
commRxPool
Indicates the resources by which the UE is allowed to receive sidelink communication while in RRC_IDLE and while in RRC_CONNECTED.
commSyncConfig
Indicates the configuration by which the UE is allowed to receive and transmit synchronisation information. E-UTRAN configures commSyncConfig including txParameters when configuring UEs by dedicated signalling to transmit synchronisation information.
commTxPoolExceptional
Indicates the resources by which the UE is allowed to transmit sidelink communication in exceptional conditions, as specified in 5.10.4.
commTxPoolNormalCommon
Indicates the resources by which the UE is allowed to transmit sidelink communication while in RRC_IDLE or when in RRC_CONNECTED while transmitting sidelink via a frequency other than the primary.
commTxAllowRelayCommon
Indicates whether the UE is allowed to transmit relay related data using the transmission pools included in SIB18 i.e. either via commTxPoolNormalCommon or via commTxPoolExceptional.

-	SystemInformationBlockType19
The IE SystemInformationBlockType19 indicates E-UTRAN supports the sidelink UE information procedure and may contain sidelink discovery related resource configuration information.
SystemInformationBlockType19 information element
-- ASN1START

SystemInformationBlockType19-r12 ::= SEQUENCE {
	discConfig-r12						SEQUENCE {
		discRxPool-r12						SL-DiscRxPoolList-r12,
		discTxPoolCommon-r12				SL-DiscTxPoolList-r12 			OPTIONAL,	-- Need OR
		discTxPowerInfo-r12				SL-DiscTxPowerInfoList-r12 	OPTIONAL,	-- Cond Tx
		discSyncConfig-r12					SL-SyncConfigList-r12		OPTIONAL	-- Need OR
	}																		OPTIONAL,	-- Need OR
	discInterFreqList-r12				SL-CarrierFreqInfoList-r12		OPTIONAL,	-- Need OR
	lateNonCriticalExtension			OCTET STRING						OPTIONAL,
	...,
	[[	discConfig-v13x0				SEQUENCE {
			discInterFreqList-v13x0			SL-CarrierFreqInfoList-v13x0	OPTIONAL,	-- Need OR
			gapRequestsAllowedCommon		ENUMERATED {true}			OPTIONAL	-- Need OR
		}																OPTIONAL,	-- Need OR
		discConfigRelay-r13				SEQUENCE {
			discThreshHiRelayUE-r13			RSRP-Range					OPTIONAL,	-- Need OR
			discThreshLoRelayUE-r13			RSRP-Range					OPTIONAL,	-- Need OR
			discHystMaxRelayUE-r13			ENUMERATED {dB0, dB3, dB6, dB9, dB12, dBinf},
			discHystMinRelayUE-r13			ENUMERATED {dB0, dB3, dB6, dB9, dB12},
				-- Uu threshold
			discThreshHiRemoteUE-r13		RSRP-Range					OPTIONAL,	-- Need OR
			discHystMaxRemoteUE-r13			ENUMERATED {dB0, dB3, dB6, dB9, dB12},
				-- Uu threshold
			reselectionInfoRemoteUE-IC-r13	ReselectionInfoRelay-r13
		}																OPTIONAL,	-- Need OR
		discConfigPS-13					SEQUENCE {
			discRxPoolPS-r13				SL-DiscRxPoolList-r12,
			discTxPoolPS-Common-r13			SL-DiscTxPoolList-r12		OPTIONAL	-- Need OR
		}																OPTIONAL	-- Need OR
	]]
}

SL-CarrierFreqInfoList-r12 ::=	SEQUENCE (SIZE (1..maxFreq)) OF SL-CarrierFreqInfo-r12

SL-CarrierFreqInfoList-v13x0 ::=	SEQUENCE (SIZE (1..maxFreq)) OF SL-CarrierFreqInfo-v13x0

SL-CarrierFreqInfo-r12::= 		SEQUENCE {
	carrierFreq-r12 					ARFCN-ValueEUTRA-r9,
	plmn-IdentityList-r12			PLMN-IdentityList4-r12			OPTIONAL	-- Need OP
}

ReselectionInfoRelay-r13 ::=	SEQUENCE {
	q-RxLevMin-r13					Q-RxLevMin,
	-- Note that the mapping of invidual values may be different for PC5, but the granularity/
	-- number of values is same as for Uu
	filterCoefficient-r13			FilterCoefficient,
	minHyst-r13					ENUMERATED {dB0, dB3,
										dB6, dB9, dB12, dBinf}	OPTIONAL	-- Need OR
}

CellSelectionInfoNFreq-r13 ::=	SEQUENCE {
	-- Cell selection information as in SIB1
	q-RxLevMin-r13					Q-RxLevMin,
	q-RxLevMinOffset					INTEGER (1..8)			OPTIONAL,	-- Need OP
	-- Cell re-selection information as in SIB3
	q-Hyst-r13							ENUMERATED {
											dB0, dB1, dB2, dB3, dB4, dB5, dB6, dB8, dB10,
											dB12, dB14, dB16, dB18, dB20, dB22, dB24},
	q-RxLevMinReselection-r13			Q-RxLevMin			OPTIONAL,	-- Need OP
	t-ReselectionEUTRA-r13				T-Reselection
}

SL-CarrierFreqInfo-v13x0::= 	SEQUENCE {
	discRxResources-r13				SL-DiscRxPoolList-r12				OPTIONAL,	-- Need OR
	discRxResourcesPS-r13			SL-DiscRxPoolList-r12				OPTIONAL,	-- Need OR
	discTxResources-r13				SL-DiscTxResourcesInterFreq-r13		OPTIONAL,	-- Need OR
	discTxResourcesPS-r13			SL-DiscTxResourcesInterFreq-r13		OPTIONAL,	-- Need OR
	discTxPowerInfo-r13				SL-DiscTxPowerInfoList-r12 			OPTIONAL,	-- Cond Tx
	discTxRefCarrierCommon-r13		ENUMERATED {pCell}					OPTIONAL,	-- Need OR
	discSyncConfig-r13				SL-SyncConfigListNFreq-r12				OPTIONAL,	-- Need OR
	cellSelectionInfo-r13			CellSelectionInfoNFreq-r13			OPTIONAL	-- Need OR
}

PLMN-IdentityList4-r12 ::=	SEQUENCE (SIZE (1..maxPLMN-r11)) OF	PLMN-IdentityInfo2-r12

PLMN-IdentityInfo2-r12 ::=		CHOICE	{
	plmn-Index-r12					INTEGER (1..maxPLMN-r11),
	plmnIdentity-r12				PLMN-Identity
}

SL-DiscTxResourcesInterFreq-r13 ::=	CHOICE {
	acquireSI-FromCarrier-r13		NULL,
	discTxPoolCommon-r13			SL-DiscTxPoolList-r12,
	requestDedicated-r13			NULL,
	noTxOnCarrier-r13				NULL
}

-- ASN1STOP

SystemInformationBlockType19 field descriptions
cellSelectionInfo
Parameters that may be used by the UE to select/ reselect a cell on the concerned non serving frequency. If absent, the UE acquires the information from the target cell on the concerned frequency.
discInterFreqList
Indicates the neighbouring frequencies on which sidelink discovery announcement is supported. May also provide further information i.e. reception resource pool and/ or transmission resource pool, or an indication how resources could be obtained.
discRxPool
Indicates the resources by which the UE is allowed to receive sidelink discovery announcements while in RRC_IDLE and while in RRC_CONNECTED.
discRxPoolPS
Indicates the resources by which the UE is allowed receive relay and other public safety related sidelink discovery announcements while in RRC_IDLE and while in RRC_CONNECTED.
discSyncConfig
Indicates the configuration by which the UE is allowed to receive and transmit synchronisation information. E-UTRAN configures discSyncConfig including txParameters when configuring UEs by dedicated signalling to transmit synchronisation information.
discThreshHiRemoteUE
Indicates when a remote UE that is in network coverage may use the broadcast PS related sidelink discovery Tx resource pool, if broadcast, or request Tx resources by dedicated signalling otherwise. The parameter equally applies for Tx resources for relay related communication.
discThreshXxRelayUE
Indicates when a relay UE that is in network coverage may use the broadcast PS related sidelink discovery Tx resource pool, if broadcast, or request Tx resources by dedicated signalling otherwise.
discTxPoolCommon
Indicates the resources by which the UE is allowed to transmit sidelink discovery announcements while in RRC_IDLE.
discTxPoolPS-Common
Indicates the resources by which the UE is allowed to transmit relay and other public safety related sidelink discovery announcements while in RRC_IDLE.
discTxRefCarrierCommon
Indicates if the PCell (RRC_CONNECTED)/ serving cell (RRC_IDLE) is to be used as reference DL measurements and synchronization, instead of the frequency used to transmit sidelink discovery announcements on, see TS 36.213 [23, 14.3.1].
plmn-IdentityList
List of PLMN identities for the neighbouring frequency indicated by carrierFreq. Absence of the field indicates the same PLMN identities as listed in plmn-IdentityList (without suffix) in SystemInformationBlockType1.
plmn-Index
Index of the corresponding entry in field plmn-IdentityList (without suffix) within SystemInformationBlockType1.
q-RxLevMinReselection
In case the field is absent, the UE shall apply q-RxLevMin.
reselectionInfoRemoteUE
Includes the parameters used by the UE when selecting/ reselecting a sidelink relay.

Conditional presence
Explanation
Tx
The field is mandatory present if discTxPoolCommon is included. Otherwise the field is optional present, need OR.

-	SystemInformationBlockType20
The IE SystemInformationBlockType20 contains the information required to acquire the control information associated transmission of MBMS using SC-PTM.
SystemInformationBlockType20 information element
-- ASN1START

SystemInformationBlockType20-r13 ::=	SEQUENCE {
	sc-mcch-RepetionPeriod-r13		ENUMERATED {rf2, rf4, rf8, rf16, rf32, rf64, rf128, rf256},
	sc-mcch-Offset-r13				INTEGER (0..10),
	sc-mcch-Subframe-r13			INTEGER (0..9),
	sc-mcch-ModificationPeriod-r13	ENUMERATED {rf2, rf4, rf8, rf16, rf32, rf64, rf128, rf256,
										 rf512, rf1024},
	lateNonCriticalExtension			OCTET STRING					OPTIONAL,
	...
}

-- ASN1STOP

SystemInformationBlockType20 field descriptions
sc-mcch-ModificationPeriod
Defines periodically appearing boundaries, i.e. radio frames for which SFN mod sc-mcch-ModificationPeriod = 0. The contents of different transmissions of SC-MCCH information can only be different if there is at least one such boundary in-between them.
sc-mcch-Offset
Indicates, together with the sc-mcch-RepetitionPeriod, the radio frames in which SC-MCCH is scheduled i.e. MCCH is scheduled in radio frames for which: SFN mod mcch-RepetitionPeriod = mcch-Offset.
sc-mcch-Subframe
Indicates the subframe in which SC-MCCH is scheduled
sc-mcch-RepetitionPeriod
Defines the interval between transmissions of SC-MCCH information, in radio frames, Value rf32 corresponds to 32 radio frames, rf64 corresponds to 64 radio frames and so on.

6.3.2	Radio resource control information elements
-	AntennaInfo
The IE AntennaInfoCommon and the AntennaInfoDedicated are used to specify the common and the UE specific antenna configuration respectively.
AntennaInfo information elements
-- ASN1START

AntennaInfoCommon ::=				SEQUENCE {
	antennaPortsCount					ENUMERATED {an1, an2, an4, spare1}
}

AntennaInfoDedicated ::=			SEQUENCE {
	transmissionMode					ENUMERATED {
											tm1, tm2, tm3, tm4, tm5, tm6,
											tm7, tm8-v920},
	codebookSubsetRestriction			CHOICE {
		n2TxAntenna-tm3						BIT STRING (SIZE (2)),
		n4TxAntenna-tm3						BIT STRING (SIZE (4)),
		n2TxAntenna-tm4						BIT STRING (SIZE (6)),
		n4TxAntenna-tm4						BIT STRING (SIZE (64)),
		n2TxAntenna-tm5						BIT STRING (SIZE (4)),
		n4TxAntenna-tm5						BIT STRING (SIZE (16)),
		n2TxAntenna-tm6						BIT STRING (SIZE (4)),
		n4TxAntenna-tm6						BIT STRING (SIZE (16))
	}		OPTIONAL, 															-- Cond TM
	ue-TransmitAntennaSelection			CHOICE{
		release							NULL,
		setup							ENUMERATED {closedLoop, openLoop}
	}
}

AntennaInfoDedicated-v920 ::=		SEQUENCE {
	codebookSubsetRestriction-v920		CHOICE {
		n2TxAntenna-tm8-r9					BIT STRING (SIZE (6)),
		n4TxAntenna-tm8-r9					BIT STRING (SIZE (32))
	}		OPTIONAL 															-- Cond TM8
}

AntennaInfoDedicated-r10 ::=		SEQUENCE {
	transmissionMode-r10				ENUMERATED {
											tm1, tm2, tm3, tm4, tm5, tm6, tm7, tm8-v920,
											tm9-v1020, tm10-v1130, spare6, spare5, spare4,
											spare3, spare2, spare1},
	codebookSubsetRestriction-r10		BIT STRING			OPTIONAL,			-- Cond TMX
	ue-TransmitAntennaSelection		CHOICE{
		release							NULL,
		setup							ENUMERATED {closedLoop, openLoop}
	}
}

AntennaInfoDedicated-v10i0::=	SEQUENCE {
	maxLayersMIMO-r10			ENUMERATED {twoLayers, fourLayers, eightLayers}		OPTIONAL	-- Need OR
}

AntennaInfoDedicated-v1250 ::=		SEQUENCE {
	alternativeCodebookEnabledFor4TX-r12	BOOLEAN
}

-- ASN1STOP

AntennaInfo field descriptions
alternativeCodebookEnabledFor4TX
Indicates whether code book in TS 36.213 [23] Table 7.2.4-0A to Table 7.2.4-0D is being used for deriving CSI feedback and reporting. E-UTRAN only configures the field if the UE is configured with a) tm8 or tm9, b) PMI/RI reporting and c) 4 CRS ports.
antennaPortsCount
Parameter represents the number of cell specific antenna ports where an1 corresponds to 1, an2 to 2 antenna ports etc. see TS 36.211 [21, 6.2.1].
codebookSubsetRestriction
Parameter: codebookSubsetRestriction, see TS 36.213 [23, 7.2] and TS 36.211 [21, 6.3.4.2.3]. The number of bits in the codebookSubsetRestriction for applicable transmission modes is defined in TS 36.213 [23, Table 7.2-1b]. If the UE is configured with transmissionMode tm8, E-UTRAN configures the field codebookSubsetRestriction if PMI/RI reporting is configured. If the UE is configured with transmissionMode tm9, E-UTRAN configures the field codebookSubsetRestriction if PMI/RI reporting is configured and if the number of CSI-RS ports is greater than 1. E-UTRAN does not configure the field codebookSubsetRestriction in other cases where the UE is configured with transmissionMode tm8 or tm9.
maxLayersMIMO
Indicates the maximum number of layers for spatial multiplexing used to determine the rank indication bit width and Kc determination of the soft buffer size for the corresponding serving cell according to TS 36.212 [22]. EUTRAN configures this field only when transmissionMode is set to tm3, tm4, tm9 or tm10 for the corresponding serving cell. When configuring the field for a serving cell which transmissionMode is set to tm3 or tm4, EUTRAN only configures value fourLayers: For a serving cell which transmissionMode is set to tm9 or tm10, EUTRAN only configures the field only if intraBandContiguousCC-InfoList is indicated for the band and the band combination of the corresponding serving cell.
transmissionMode
Points to one of Transmission modes defined in TS 36.213 [23, 7.1] where tm1 refers to transmission mode 1, tm2 to transmission mode 2 etc.
ue-TransmitAntennaSelection
For value setup the field indicates whether UE transmit antenna selection control is closed-loop or open-loop as described in TS 36.213 [23, 8.7]. EUTRAN configures the same value for all serving cells.

Conditional presence
Explanation
TM
The field is mandatory present if the transmissionMode is set to tm3, tm4, tm5 or tm6. Otherwise the field is not present and the UE shall delete any existing value for this field.
TM8
The field is optional present, need OR, if AntennaInfoDedicated is included and transmissionMode is set to tm8. If AntennaInfoDedicated is included and transmissionMode is set to a value other than tm8, the field is not present and the UE shall delete any existing value for this field. Otherwise the field is not present.
TMX
The field is mandatory present if the transmissionMode-r10 is set to tm3, tm4, tm5 or tm6. The field is optionally present, need OR, if the transmissionMode-r10 is set to tm8 or tm9. Otherwise the field is not present and the UE shall delete any existing value for this field.

-	AntennaInfoUL
The IE AntennaInfoUL is used to specify the UL antenna configuration.
AntennaInfoUL information elements
-- ASN1START

AntennaInfoUL-r10 ::=		SEQUENCE {
	transmissionModeUL-r10				ENUMERATED {tm1, tm2, spare6, spare5,
													spare4, spare3, spare2, spare1}	OPTIONAL,	-- Need OR
	fourAntennaPortActivated-r10			ENUMERATED {setup}			OPTIONAL		-- Need OR
}

-- ASN1STOP

AntennaInfoUL field descriptions
fourAntennaPortActivated
Parameter indicates if four antenna ports are used. See TS 36.213 [23, 8.2]. E-UTRAN optionally configures fourAntennaPortActivated only if transmissionModeUL is set to tm2.
transmissionModeUL
Points to one of UL Transmission modes defined in TS 36.213 [23, 8.0] where tm1 refers to transmission mode 1, tm2 to transmission mode 2 etc.

-	CQI-ReportConfig
The IE CQI-ReportConfig is used to specify the CQI reporting configuration.
CQI-ReportConfig information elements
-- ASN1START

CQI-ReportConfig ::=				SEQUENCE {
	cqi-ReportModeAperiodic			CQI-ReportModeAperiodic	OPTIONAL,			-- Need OR
	nomPDSCH-RS-EPRE-Offset				INTEGER (-1..6),
	cqi-ReportPeriodic				CQI-ReportPeriodic	OPTIONAL				-- Need ON
}

CQI-ReportConfig-v920 ::=		SEQUENCE {
	cqi-Mask-r9						ENUMERATED {setup}		OPTIONAL,		-- Cond cqi-Setup
	pmi-RI-Report-r9				ENUMERATED {setup}		OPTIONAL		-- Cond PMIRI
}

CQI-ReportConfig-r10 ::=	SEQUENCE {
	cqi-ReportAperiodic-r10				CQI-ReportAperiodic-r10			OPTIONAL,	-- Need ON
	nomPDSCH-RS-EPRE-Offset			INTEGER (-1..6),
	cqi-ReportPeriodic-r10				CQI-ReportPeriodic-r10			OPTIONAL,	-- Need ON
	pmi-RI-Report-r9					ENUMERATED {setup}				OPTIONAL,	-- Cond PMIRIPCell
	csi-SubframePatternConfig-r10		CHOICE {
		release							NULL,
		setup							SEQUENCE {
			csi-MeasSubframeSet1-r10			MeasSubframePattern-r10,
			csi-MeasSubframeSet2-r10			MeasSubframePattern-r10
		}
	}																	OPTIONAL	-- Need ON
}

CQI-ReportConfig-v1130 ::=	SEQUENCE {
	cqi-ReportPeriodic-v1130			CQI-ReportPeriodic-v1130,
	cqi-ReportBoth-r11					CQI-ReportBoth-r11
}

CQI-ReportConfig-v1250 ::=		SEQUENCE {
	csi-SubframePatternConfig-r12		CHOICE {
		release							NULL,
		setup							SEQUENCE {
			csi-MeasSubframeSets-r12			BIT STRING (SIZE (10))
		}
	}																OPTIONAL,	-- Need ON
	cqi-ReportBoth-v1250					CQI-ReportBoth-v1250		OPTIONAL, 	-- Need ON
	cqi-ReportAperiodic-v1250	CQI-ReportAperiodic-v1250		OPTIONAL,	-- Need ON
	altCQI-Table-r12			ENUMERATED {
									allSubframes, csi-SubframeSet1,
									csi-SubframeSet2, spare1}		OPTIONAL		-- Need OP
}

CQI-ReportConfig-v13xy ::=			SEQUENCE {
	cqi-ReportAperiodic-v13xy			CQI-ReportAperiodic-v13xy	OPTIONAL,		-- Need ON
	cqi-ReportPeriodic-v13xy			CQI-ReportPeriodic-v13xy 		OPTIONAL		-- Need ON
}

CQI-ReportConfigSCell-r10 ::=				SEQUENCE {
	cqi-ReportModeAperiodic-r10			CQI-ReportModeAperiodic OPTIONAL,			-- Need OR
	nomPDSCH-RS-EPRE-Offset-r10				INTEGER (-1..6),
	cqi-ReportPeriodicSCell-r10			CQI-ReportPeriodic-r10			OPTIONAL,	-- Need ON
	pmi-RI-Report-r10					ENUMERATED {setup}				OPTIONAL	-- Cond PMIRISCell
}

CQI-ReportConfigSCell-v13x0 ::=		SEQUENCE {
	cqi-ReportPeriodicSCell-v13x0			CQI-ReportPeriodic-v13xy
}

CQI-ReportPeriodic ::=		CHOICE {
	release							NULL,
	setup							SEQUENCE {
		cqi-PUCCH-ResourceIndex				INTEGER (0..1185),
		cqi-pmi-ConfigIndex					INTEGER (0..1023),
		cqi-FormatIndicatorPeriodic			CHOICE {
			widebandCQI							NULL,
			subbandCQI							SEQUENCE {
				k									INTEGER (1..4)
			}
		},
		ri-ConfigIndex						INTEGER (0..1023) 	OPTIONAL, 				-- Need OR
		simultaneousAckNackAndCQI			BOOLEAN
	}
}

CQI-ReportPeriodic-r10 ::=		CHOICE {
	release								NULL,
	setup								SEQUENCE {
		cqi-PUCCH-ResourceIndex-r10			INTEGER (0..1184),
		cqi-PUCCH-ResourceIndexP1-r10		INTEGER (0..1184)				OPTIONAL,	-- Need OR
		cqi-pmi-ConfigIndex				INTEGER (0..1023),
		cqi-FormatIndicatorPeriodic-r10		CHOICE {
			widebandCQI-r10						SEQUENCE {
				csi-ReportMode-r10		ENUMERATED {submode1, submode2}		OPTIONAL	-- Need OR
			},
			subbandCQI-r10						SEQUENCE {
				k								INTEGER (1..4),
				periodicityFactor-r10				ENUMERATED {n2, n4}
			}
		},
		ri-ConfigIndex					INTEGER (0..1023)		OPTIONAL,				-- Need OR
		simultaneousAckNackAndCQI		BOOLEAN,
		cqi-Mask-r9						ENUMERATED {setup}		OPTIONAL,				-- Need OR
		csi-ConfigIndex-r10				CHOICE {
			release							NULL,
			setup							SEQUENCE {
				cqi-pmi-ConfigIndex2-r10		INTEGER (0..1023),
				ri-ConfigIndex2-r10				INTEGER (0..1023)		OPTIONAL		-- Need OR
			}
		}		OPTIONAL																-- Need ON
	}
}


CQI-ReportPeriodic-v1130 ::=	SEQUENCE {
	simultaneousAckNackAndCQI-Format3-r11		ENUMERATED {setup}		OPTIONAL,	-- Need OR
	cqi-ReportPeriodicProcExtToReleaseList-r11	CQI-ReportPeriodicProcExtToReleaseList-r11	OPTIONAL,	-- Need ON
	cqi-ReportPeriodicProcExtToAddModList-r11	CQI-ReportPeriodicProcExtToAddModList-r11	OPTIONAL	-- Need ON
}

CQI-ReportPeriodic-v13xy ::=	SEQUENCE {
	cri-ReportConfig-r13			CRI-ReportConfig-r13				OPTIONAL,	-- Need ON
	simultaneousAckNackAndCQI-Format4-Format5-r13		ENUMERATED {setup}		OPTIONAL-- Need OR
}


CQI-ReportPeriodicProcExtToAddModList-r11 ::=		SEQUENCE (SIZE (1..maxCQI-ProcExt-r11)) OF CQI-ReportPeriodicProcExt-r11

CQI-ReportPeriodicProcExtToReleaseList-r11 ::=	SEQUENCE (SIZE (1..maxCQI-ProcExt-r11)) OF CQI-ReportPeriodicProcExtId-r11

CQI-ReportPeriodicProcExt-r11 ::=		SEQUENCE {
	cqi-ReportPeriodicProcExtId-r11	CQI-ReportPeriodicProcExtId-r11,
	cqi-pmi-ConfigIndex-r11			INTEGER (0..1023),
	cqi-FormatIndicatorPeriodic-r11	CHOICE {
		widebandCQI-r11				SEQUENCE {
			csi-ReportMode-r11			ENUMERATED {submode1, submode2}	OPTIONAL	-- Need OR
		},
		subbandCQI-r11				SEQUENCE {
			k							INTEGER (1..4),
			periodicityFactor-r11		ENUMERATED {n2, n4}
		}
	},
	ri-ConfigIndex-r11				INTEGER (0..1023)					OPTIONAL,	-- Need OR
	csi-ConfigIndex-r11				CHOICE {
		release							NULL,
		setup							SEQUENCE {
			cqi-pmi-ConfigIndex2-r11		INTEGER (0..1023),
			ri-ConfigIndex2-r11				INTEGER (0..1023)		OPTIONAL		-- Need OR
		}
	}																OPTIONAL,		-- Need ON
	...,
	[[	cri-ReportConfig-r13			CRI-ReportConfig-r13				OPTIONAL	-- Need ON
	]]
}

CQI-ReportAperiodic-r10	::=		CHOICE {
	release								NULL,
	setup								SEQUENCE {
		cqi-ReportModeAperiodic-r10			CQI-ReportModeAperiodic,
		aperiodicCSI-Trigger-r10			SEQUENCE {	
			trigger1-r10					BIT STRING (SIZE (8)),
			trigger2-r10					BIT STRING (SIZE (8))
		}																	 OPTIONAL	-- Need OR
	}
}

CQI-ReportAperiodic-v1250	::=		CHOICE {
	release								NULL,
	setup								SEQUENCE {
		aperiodicCSI-Trigger-v1250			SEQUENCE {	
			trigger-SubframeSetIndicator-r12	ENUMERATED {s1, s2},
			trigger1-SubframeSetIndicator-r12	BIT STRING (SIZE (8)),
			trigger2-SubframeSetIndicator-r12	BIT STRING (SIZE (8))
		}
	}
}

CQI-ReportAperiodic-v13xy  	::=		CHOICE {
	release								NULL,
	setup								SEQUENCE {
		cqi-ReportModeAperiodic-r13		CQI-ReportModeAperiodic,
		aperiodicCSI-Trigger-v13xy			SEQUENCE {	
			trigger1-r13					BIT STRING (SIZE (32)),
			trigger2-r13					BIT STRING (SIZE (32)),
			trigger3-r13					BIT STRING (SIZE (32)),
			trigger4-r13					BIT STRING (SIZE (32)),
			trigger5-r13					BIT STRING (SIZE (32)),
			trigger6-r13					BIT STRING (SIZE (32))
		}																	 OPTIONAL,	-- Need OR
		aperiodicCSI-Trigger2-r13		SEQUENCE {	
			trigger1-SubframeSetIndicator-r13	BIT STRING (SIZE (32)),
			trigger2-SubframeSetIndicator-r13	BIT STRING (SIZE (32)),
			trigger3-SubframeSetIndicator-r13	BIT STRING (SIZE (32)),
			trigger4-SubframeSetIndicator-r13	BIT STRING (SIZE (32)),
			trigger5-SubframeSetIndicator-r13	BIT STRING (SIZE (32)),
			trigger6-SubframeSetIndicator-r13	BIT STRING (SIZE (32))
		}																	 OPTIONAL	-- Need OR
	}
}

CQI-ReportAperiodicProc-r11	::=		SEQUENCE {
	cqi-ReportModeAperiodic-r11			CQI-ReportModeAperiodic,
	trigger01-r11						BOOLEAN,
	trigger10-r11						BOOLEAN,
	trigger11-r11						BOOLEAN
}

CQI-ReportAperiodicProc-r13	::=		SEQUENCE {
	trigger001-r13						BOOLEAN,
	trigger010-r13						BOOLEAN,
	trigger011-r13						BOOLEAN,
	trigger100-r13						BOOLEAN,	
	trigger101-r13						BOOLEAN,
	trigger110-r13						BOOLEAN,
	trigger111-r13						BOOLEAN}

CQI-ReportModeAperiodic ::=				ENUMERATED {
											rm12, rm20, rm22, rm30, rm31,
											rm32-v1250, rm10-v13xy, rm11-v13xx
}

CQI-ReportBoth-r11 ::=			SEQUENCE {
	csi-IM-ConfigToReleaseList-r11		CSI-IM-ConfigToReleaseList-r11	OPTIONAL,	-- Need ON
	csi-IM-ConfigToAddModList-r11		CSI-IM-ConfigToAddModList-r11	OPTIONAL,	-- Need ON
	csi-ProcessToReleaseList-r11		CSI-ProcessToReleaseList-r11	OPTIONAL,	-- Need ON
	csi-ProcessToAddModList-r11			CSI-ProcessToAddModList-r11		OPTIONAL	-- Need ON
}

CQI-ReportBoth-v1250 ::=			SEQUENCE {
	csi-IM-ConfigToReleaseListExt-r12		CSI-IM-ConfigId-v1250	OPTIONAL,	-- Need ON
	csi-IM-ConfigToAddModListExt-r12		CSI-IM-ConfigExt-r12	OPTIONAL	-- Need ON
}

CSI-IM-ConfigToAddModList-r11 ::=		SEQUENCE (SIZE (1..maxCSI-IM-r11)) OF CSI-IM-Config-r11

CSI-IM-ConfigToReleaseList-r11 ::=		SEQUENCE (SIZE (1..maxCSI-IM-r11)) OF CSI-IM-ConfigId-r11

CSI-ProcessToAddModList-r11 ::=		SEQUENCE (SIZE (1..maxCSI-Proc-r11)) OF CSI-Process-r11

CSI-ProcessToReleaseList-r11 ::=	SEQUENCE (SIZE (1..maxCSI-Proc-r11)) OF CSI-ProcessId-r11

CQI-ReportBothProc-r11 ::=			SEQUENCE {
	ri-Ref-CSI-ProcessId-r11			CSI-ProcessId-r11				OPTIONAL,		-- Need OR
	pmi-RI-Report-r11					ENUMERATED {setup}				OPTIONAL		-- Need OR
}

CRI-ReportConfig-r13 ::=			CHOICE {
	release								NULL,
	setup								SEQUENCE {
		cri-ConfigIndex-r13					ENUMERATED {n1, n2, n4, n8, n16, n32},
		cri-ConfigIndex2-r13				ENUMERATED {n1, n2, n4, n8, n16, n32}	OPTIONAL	-- Need OR
	}
}

-- ASN1STOP

CQI-ReportConfig field descriptions
altCQI-Table
Indicates the applicability of the alternative CQI table (i.e. Table 7.2.3-2 in TS 36.213 [23]) for both aperiodic and periodic CSI reporting for the concerned serving cell. Value allSubframes means the alternative CQI table applies to all the subframes and CSI processes, if configured, and value csi-SubframeSet1 means the alternative CQI table applies to CSI subframe set1, and value csi-SubframeSet2 means the alternative CQI table applies to CSI subframe set2. EUTRAN sets the value to csi-SubframeSet1 or csi-SubframeSet2 only if transmissionMode is set in range tm1 to tm9 and csi-SubframePatternConfig-r10 is configured for the concerned serving cell and different CQI tables apply to the two CSI subframe sets; otherwise EUTRAN sets the value to allSubframes. If this field is not present, the UE shall use Table 7.2.3-1 in TS 36.213 [23] for all subframes and CSI processes, if configured.
aperiodicCSI-Trigger
Indicates for which serving cell(s) the aperiodic CSI report is triggered when one or more SCells are configured. trigger1 corresponds to the CSI request field 10 and trigger2 corresponds to the CSI request field 11, see TS 36.213 [23, table 7.2.1-1A], and so on. The leftmost bit, bit 0 in the bit string corresponds to the cell with ServCellIndex=0 and bit 1 in the bit string corresponds to the cell with ServCellIndex=1 etc. Each bit has either value 0 (means no aperiodic CSI report is triggered) or value 1 (means the aperiodic CSI report is triggered). At most 5 bits can be set to value 1 in the bit string in aperidociCSI-Trigger-r10. E-UTRAN configures value 1 only for cells configured with transmissionMode set in range tm1 to tm9. One value applies for all serving cells configured with transmissionMode set in range tm1 to tm9 (the associated functionality is common i.e. not performed independently for each cell).
cqi-Mask
Limits CQI/PMI/PTI/RI reports to the on-duration period of the DRX cycle, see TS 36.321 [6]. One value applies for all CSI processes and all serving cells (the associated functionality is common i.e. not performed independently for each cell).
cqi-FormatIndicatorPeriodic
Parameter: PUCCH CQI Feedback Type, see TS 36.213 [23, table 7.2.2-1]. Depending on transmissionMode, reporting mode is implicitly given from the table.
cqi-pmi-ConfigIndex
Parameter: CQI/PMI Periodicity and Offset Configuration Index ICQI/PMI, see TS 36.213 [23, tables 7.2.2-1A and 7.2.2-1C]. If subframe patterns for CSI (CQI/PMI/PTI/RI) reporting are configured (i.e. csi-SubframePatternConfig is configured), the parameter applies to the subframe pattern corresponding to csi-MeasSubframeSet1 or corresponding to the CSI subframe set 1 indicated by csi-MeasSubframeSets-r12.
cqi-pmi-ConfigIndex2
Parameter: CQI/PMI Periodicity and Offset Configuration Index ICQI/PMI, see TS 36.213 [23, tables 7.2.2-1A and 7.2.2-1C]. The parameter applies to the subframe pattern corresponding to csi-MeasSubframeSet2 or corresponding to the CSI subframe set 2 indicated by csi-MeasSubframeSets-r12.
cqi-PUCCH-ResourceIndex, cqi-PUCCH-ResourceIndexP1
Parameter for antenna port P0 and for antenna port P1 respectively, see TS 36.213 [23, 7.2]. E-UTRAN does not apply value 1185. One value applies for all CSI processes.
cqi-ReportAperiodic
E-UTRAN does not configure CQI-ReportAperiodic when transmission mode 10 is configured for all serving cells. E-UTRAN configures cqi-ReportAperiodic-v1250 only if cqi-ReportAperiodic-r10 and csi-MeasSubframeSets-r12 are configured.
cqi-ReportModeAperiodic
Parameter: reporting mode. Value rm12 corresponds to Mode 1-2, rm20 corresponds to Mode 2-0, rm22 corresponds to Mode 2-2 etc. PUSCH reporting modes are described in TS 36.213 [23, 7.2.1]. The UE shall ignore cqi-ReportModeAperiodic-r10 when transmission mode 10 is configured for the serving cell on this carrier frequency. The UE shall ignore cqi-ReportModeAperiodic-r10 configured for the PCell/ PSCell when the transmission bandwidth of the PCell/PSCell in downlink is 6 resource blocks.
CQI-ReportPeriodicProcExt
A set of periodic CQI related parameters for which E-UTRAN may configure different values for each CSI process. For a serving frequency E-UTRAN configures one or more CQI-ReportPeriodicProcExt only when transmission mode 10 is configured for the serving cell on this carrier frequency.
cri-ConfigIndex2
Parameter: CRI Config Index ICRI, see TS 36.213 []. The parameter applies to the subframe pattern corresponding to csi-MeasSubframeSet2 or corresponding to the CSI subframe set 2 indicated by csi-MeasSubframeSets. E-UTRAN configures cri-ConfigIndex2 only if cri-ConfigIndex is configured.
cri-ReportConfig
E-UTRAN configures the field only if the UE is configured with eMIMO-Type set to beamformed and if multiple references to RS configuration using non-zero power transmission are configured (i.e. if csi-RS-ConfigNZPIdListExt is configured).
csi-ConfigIndex
E-UTRAN configures csi-ConfigIndex only for PCell and only if csi-SubframePatternConfig is configured. The UE shall release csi-ConfigIndex if csi-SubframePatternConfig is released.
csi-IM-ConfigToAddModList
For a serving frequency E-UTRAN configures one or more CSI-IM-Config only when transmission mode 10 is configured for the serving cell on this carrier frequency.
csi-MeasSubframeSets
Indicates the two CSI subframe sets. Value 0 means the subframe belongs to CSI subframe set 1 and value 1 means the subframe belongs to CSI subframe set 2. CSI subframe set 1 refers to CCSI,0 in TS 36.213 [23, 7.2] and CSI subframe set 2 refers to CCSI,1 in TS 36.213 [23, 7.2]. EUTRAN does not configure csi-MeasSubframeSet1-r10 and csi-MeasSubframeSet2-r10 if either csi-MeasSubframeSets-r12 for PCell or eimta-MainConfigPCell-r12 is configured.
csi-MeasSubframeSet1, csi-MeasSubframeSet2
Indicates the CSI measurement subframe sets. csi-MeasSubframeSet1 refers to CCSI,0 in TS 36.213 [23, 7.2] and csi-MeasSubframeSet2 refers to CCSI,1 in TS 36.213 [23, 7.2]. E-UTRAN only configures the two CSI measurement subframe sets for the PCell.
csi-ProcessToAddModList
For a serving frequency E-UTRAN configures one or more CSI-Process only when transmission mode 10 is configured for the serving cell on this carrier frequency.
csi-ReportMode
Parameter: PUCCH_format1-1_CSI_reporting_mode, see TS 36.213 [23, 7.2.2].
K
Parameter: K, see TS 36.213 [23, 7.2.2].
nomPDSCH-RS-EPRE-Offset
Parameter:  see TS 36.213 [23, 7.2.3]. Actual value = IE value * 2 [dB].
periodicityFactor
Parameter: , see TS 36.213 [23, 7.2.2].
pmi-RI-Report
See TS 36.213 [23, 7.2]. The presence of this field means PMI/RI reporting is configured; otherwise the PMI/RI reporting is not configured. EUTRAN configures this field only when transmissionMode is set to tm8, tm9 or tm10. The UE shall ignore pmi-RI-Report-r9/ pmi-RI-Report-r10 when transmission mode 10 is configured for the serving cell on this carrier frequency.
ri-ConfigIndex
Parameter: RI Config Index IRI, see TS 36.213 [23, 7.2.2-1B]. If subframe patterns for CSI (CQI/PMI/PTI/RI) reporting are configured (i.e. csi-SubframePatternConfig is configured), the parameter applies to the subframe pattern corresponding to csi-MeasSubframeSet1.
ri-ConfigIndex2
Parameter: RI Config Index IRI, see TS 36.213 [23, 7.2.2-1B]. The parameter applies to the subframe pattern corresponding to csi-MeasSubframeSet2 or corresponding to the CSI subframe set 2 indicated by csi-MeasSubframeSets-r12. E-UTRAN configures ri-ConfigIndex2 only if ri-ConfigIndex is configured.
ri-Ref-CSI-ProcessId
CSI process whose RI value the UE inherits when reporting RI, in the same subframe, for CSI reporting. E-UTRAN ensures that the CSI process that inherits the RI value is configured in accordance with the conditions specified in 36.213 [23, 7.2.1, 7.2.2].
simultaneousAckNackAndCQI
Parameter: Simultaneous-AN-and-CQI, see TS 36.213 [23, 10.1]. TRUE indicates that simultaneous transmission of ACK/NACK and CQI is allowed. One value applies for all CSI processes. For SCells except for the PSCell and PUCCH SCell this field is not applicable and the UE shall ignore the value.
simultaneousAckNackAndCQI-Format3
Indicates that the UE shall perform simultaneous transmission of HARQ A/N and periodic CQI report multiplexing on PUCCH format 3, see TS 36.213 [23, 7.2, 10.1.1]. E-UTRAN configures this information only when pucch-Format is set to format3. One value applies for all CSI processes. For SCells except for the PSCell and PUCCH SCell this field is not applicable and the UE shall ignore the value.
simultaneousAckNackAndCQI-Format4-Format5
Indicates that the UE shall perform simultaneous transmission of HARQ A/N and periodic CSI report multiplexing on PUCCH format 4 and format 5, see TS 36.213 [23, x.y]. E-UTRAN configures this information only when pucch-Format is set to format4 or format5. One value applies for all CSI processes. For SCells except for the PSCell and PUCCH SCell this field is not applicable and the UE shall ignore the value.
trigger01
Indicates whether or not reporting for this CSI-process or reporting for this CSI-process corresponding to a CSI subframe set is triggered by CSI request field set to 01, for a CSI request applicable for the serving cell on the same frequency as the CSI process, see TS 36.213 [23, table 7.2.1-1B].
trigger10, trigger11
Indicates whether or not reporting for this CSI-process or reporting for this CSI-process corresponding to a CSI subframe set is triggered by CSI request field set to 10 or 11, see TS 36.213 [23, table 7.2.1-1B]. EUTRAN configures at most 5 CSI processes, across all serving frequencies within each CG, to be triggered by a CSI request field set to value 10. The same restriction applies for value 11. In case E-UTRAN simultaneously triggers CSI requests for more than 5 CSI processes some limitations apply, see TS 36.213 [23].
trigger001
Indicates whether or not reporting for this CSI-process or reporting for this CSI-process corresponding to a CSI subframe set is triggered by CSI request field set to 001, for a CSI request applicable for the serving cell on the same frequency as the CSI process, see TS 36.213 [23, table 7.2.1-1B].
trigger010, trigger011, trigger100, trigger101, Trigger110, Trigger111
Indicates whether or not reporting for this CSI-process or reporting for this CSI-process corresponding to a CSI subframe set is triggered by CSI request field set to 010, 011, 100, 101, 110 or 111, see TS 36.213 [23, table 7.2.1-1B].
trigger-SubframeSetIndicator
For a serving cell configured with csi-MeasSubframeSets-r12, indicates for which CSI subframe set the aperiodic CSI report is triggered for the serving cell if the aperiodic CSI is triggered by the CSI request field 01, see TS 36.213 [23, table 7.2.1-1C]. Value s1 corresponds to CSI subframe set 1 and value s2 corresponds to CSI subframe set 2.
trigger1-SubframeSetIndicator
Indicates for which CSI subframe set the aperiodic CSI report is triggered when aperiodic CSI is triggered by the CSI request field 10, see TS 36.213 [23, table 7.2.1-1C].The leftmost bit, bit 0 in the bit string corresponds to the cell with ServCellIndex=0 and bit 1 in the bit string corresponds to the cell with ServCellIndex=1 etc. Each bit has either value 0 (means that aperiodic CSI report is triggered for CSI subframe set 1) or value 1 (means that aperiodic CSI report is triggered for CSI subframe set 2).
trigger2-SubframeSetIndicator
Indicates for which CSI subframe set the aperiodic CSI report is triggered when aperiodic CSI is triggered by the CSI request field 11, see TS 36.213 [23, table 7.2.1-1C].The leftmost bit, bit 0 in the bit string corresponds to the cell with ServCellIndex=0 and bit 1 in the bit string corresponds to the cell with ServCellIndex=1 etc. Each bit has either value 0 (means that aperiodic CSI report is triggered for CSI subframe set 1) or value 1 (means that aperiodic CSI report is triggered for CSI subframe set 2).
trigger3-SubframeSetIndicator
Indicates for which CSI subframe set the aperiodic CSI report is triggered when aperiodic CSI is triggered by the CSI request field xy, see TS 36.213 [23, table Y].The leftmost bit, bit 0 in the bit string corresponds to the cell with ServCellIndex=0 and bit 1 in the bit string corresponds to the cell with I=1 etc. Each bit has either value 0 (means that aperiodic CSI report is triggered for CSI subframe set 1) or value 1 (means that aperiodic CSI report is triggered for CSI subframe set 2).
trigger4-SubframeSetIndicator
Indicates for which CSI subframe set the aperiodic CSI report is triggered when aperiodic CSI is triggered by the CSI request field xy, see TS 36.213 [23, table Y].The leftmost bit, bit 0 in the bit string corresponds to the cell with ServCellIndex=0 and bit 1 in the bit string corresponds to the cell with I=1 etc. Each bit has either value 0 (means that aperiodic CSI report is triggered for CSI subframe set 1) or value 1 (means that aperiodic CSI report is triggered for CSI subframe set 2).
trigger5-SubframeSetIndicator
Indicates for which CSI subframe set the aperiodic CSI report is triggered when aperiodic CSI is triggered by the CSI request field xy, see TS 36.213 [23, table Y].The leftmost bit, bit 0 in the bit string corresponds to the cell with ServCellIndex=0 and bit 1 in the bit string corresponds to the cell with I=1 etc. Each bit has either value 0 (means that aperiodic CSI report is triggered for CSI subframe set 1) or value 1 (means that aperiodic CSI report is triggered for CSI subframe set 2).
trigger6-SubframeSetIndicator
Indicates for which CSI subframe set the aperiodic CSI report is triggered when aperiodic CSI is triggered by the CSI request field xy, see TS 36.213 [23, table Y].The leftmost bit, bit 0 in the bit string corresponds to the cell with ServCellIndex=0 and bit 1 in the bit string corresponds to the cell with I=1 etc. Each bit has either value 0 (means that aperiodic CSI report is triggered for CSI subframe set 1) or value 1 (means that aperiodic CSI report is triggered for CSI subframe set 2).

Conditional presence
Explanation
cqi-Setup
This field is not present for an Scell except for the PSCell, while it is conditionally present for the PCell and the PSCell according to the following. The field is optional present, need OR, if the cqi-ReportPeriodic in the cqi-ReportConfig is set to setup. If the field cqi-ReportPeriodic is present and set to release, the field is not present and the UE shall delete any existing value for this field. Otherwise the field is not present.
PMIRI
The field is optional present, need OR, if cqi-ReportPeriodic is included and set to setup, or cqi-ReportModeAperiodic is included. If the field cqi-ReportPeriodic is present and set to release and cqi-ReportModeAperiodic is absent, the field is not present and the UE shall delete any existing value for this field. Otherwise the field is not present.
PMIRIPCell
The field is optional present, need OR, if cqi-ReportPeriodic is included in the CQI-ReportConfig-r10 and set to setup, or cqi-ReportAperiodic is included in the CQI-ReportConfig-r10 and set to setup. If the field cqi-ReportPeriodic is present in the CQI-ReportConfig-r10 and set to release and cqi-ReportAperiodic is included in the CQI-ReportConfig-r10 and set to release, the field is not present and the UE shall delete any existing value for this field. Otherwise the field is not present.
PMIRISCell
The field is optional present, need OR, if cqi-ReportPeriodicSCell is included and set to setup, or cqi-ReportModeAperiodic-r10 is included in the CQI-ReportConfigSCell. If the field cqi-ReportPeriodicSCell is present and set to release and cqi-ReportModeAperiodic-r10 is absent in the CQI-ReportConfigSCell, the field is not present and the UE shall delete any existing value for this field. Otherwise the field is not present.

-	CQI-ReportPeriodicProcExtId
The IE CQI-ReportPeriodicProcExtId is used to identify a periodic CQI reporting configuration that E-UTRAN may configure in addition to the configuration specified by the IE CQI-ReportPeriodic-r10. These additional configurations are specified by the IE CQI-ReportPeriodicProcExt-r11. The identity is unique within the scope of a carrier frequency.
CQI-ReportPeriodicProcExtId information elements
-- ASN1START

CQI-ReportPeriodicProcExtId-r11 ::=					INTEGER (1..maxCQI-ProcExt-r11)

-- ASN1STOP

-	CrossCarrierSchedulingConfig
The IE CrossCarrierSchedulingConfig is used to specify the configuration when the cross carrier scheduling is used in a cell.
CrossCarrierSchedulingConfig information elements
-- ASN1START

CrossCarrierSchedulingConfig-r10 ::=		SEQUENCE {
	schedulingCellInfo-r10				CHOICE {
		own-r10								SEQUENCE {					-- No cross carrier scheduling
			cif-Presence-r10						BOOLEAN
		},
		other-r10								SEQUENCE {					-- Cross carrier scheduling
			schedulingCellId-r10				ServCellIndex-r10,
			pdsch-Start-r10						INTEGER (1..4)
		}
	}
}

CrossCarrierSchedulingConfig-r13 ::=		SEQUENCE {
	schedulingCellInfo-r13				CHOICE {
		own-r13								SEQUENCE {					-- No cross carrier scheduling
			cif-Presence-r13						BOOLEAN
		},
		other-r13							SEQUENCE {					-- Cross carrier scheduling
			schedulingCellId-r13				ServCellIndexFull-r13,
			pdsch-Start-r13						INTEGER (1..4),
			cif-InSchedulingCell-r13				INTEGER (1..7)
		}
	}
}

-- ASN1STOP

CrossCarrierSchedulingConfig field descriptions
cif-Presence
The field is used to indicate whether carrier indicator field is present (value TRUE) or not (value FALSE) in PDCCH/ EPDCCH DCI formats, see TS 36.212 [22, 5.3.3.1]. 
cif- InSchedulingCell
The field indicates the CIF value used in the scheduling cell to indicate this cell, see TS 36.212 [22, 5.3.3.1]. 
pdsch-Start
The starting OFDM symbol of PDSCH for the concerned SCell, see TS 36.213 [23. 7.1.6.4]. Values 1, 2, 3 are applicable when dl-Bandwidth for the concerned SCell is greater than 10 resource blocks, values 2, 3, 4 are applicable when dl-Bandwidth for the concerned SCell is less than or equal to 10 resource blocks, see TS 36.211 [21, Table 6,7-1].
schedulingCellId
Indicates which cell signals the downlink allocations and uplink grants, if applicable, for the concerned SCell. In case the UE is configured with DC, the scheduling cell is part of the same cell group (i.e. MCG or SCG) as the scheduled cell.

-	CSI-IM-Config
The IE CSI-IM-Config is the CSI Interference Measurement (IM) configuration that E-UTRAN may configure on a serving frequency, see TS 36.213 [23, 7.2.6].
CSI-IM-Config information elements
-- ASN1START

CSI-IM-Config-r11 ::=		SEQUENCE {
	csi-IM-ConfigId-r11			CSI-IM-ConfigId-r11,
	resourceConfig-r11			INTEGER (0..31),
	subframeConfig-r11			INTEGER (0..154),
	...
}

CSI-IM-ConfigExt-r12 ::=		SEQUENCE {
	csi-IM-ConfigId-v1250			CSI-IM-ConfigId-v1250,
	resourceConfig-r12			INTEGER (0..31),
	subframeConfig-r12			INTEGER (0..154),
	...
}

-- ASN1STOP

CSI-IM-Config field descriptions
resourceConfig
Parameter: CSI reference signal configuration, see TS 36.213 [23, 7.2.6] and TS 36.211 [21, table 6.10.5.2-1 and 6.10.5.2-2] for 4 REs.
subframeConfig
Parameter: , see TS 36.213 [23, 7.2.6] and TS 36.211 [21, table 6.10.5.3-1].

-	CSI-IM-ConfigId
The IE CSI-IM-ConfigId is used to identify a CSI-IM configuration that is configured by the IE CSI-IM-Config. The identity is unique within the scope of a carrier frequency.
CSI-IM-ConfigId information elements
-- ASN1START

CSI-IM-ConfigId-r11 ::=					INTEGER (1..maxCSI-IM-r11)
CSI-IM-ConfigId-r12 ::=					INTEGER (1..maxCSI-IM-r12)
CSI-IM-ConfigId-v1250 ::=				INTEGER (maxCSI-IM-r12)

-- ASN1STOP

-	CSI-Process
The IE CSI-Process is the CSI process configuration that E-UTRAN may configure on a serving frequency.
CSI-Process information elements
-- ASN1START

CSI-Process-r11 ::=		SEQUENCE {
	csi-ProcessId-r11			CSI-ProcessId-r11,
	csi-RS-ConfigNZPId-r11		CSI-RS-ConfigNZPId-r11,
	csi-IM-ConfigId-r11			CSI-IM-ConfigId-r11,
	p-C-AndCBSRList-r11	SEQUENCE (SIZE (1..2)) OF P-C-AndCBSR-r11,
	cqi-ReportBothProc-r11		CQI-ReportBothProc-r11			OPTIONAL,		-- Need OR
	cqi-ReportPeriodicProcId-r11	INTEGER (0..maxCQI-ProcExt-r11)		OPTIONAL,		-- Need OR
	cqi-ReportAperiodicProc-r11	CQI-ReportAperiodicProc-r11		OPTIONAL,		-- Need OR
	...,
	[[	alternativeCodebookEnabledFor4TXProc-r12	ENUMERATED {true}	OPTIONAL,	-- Need ON
		csi-IM-ConfigIdList-r12		CHOICE {
			release						NULL,
			setup						SEQUENCE (SIZE (1..2)) OF CSI-IM-ConfigId-r12
		}														OPTIONAL,	-- Need ON
		cqi-ReportAperiodicProc2-r12	CHOICE {
			release						NULL,
			setup						CQI-ReportAperiodicProc-r11
		}														OPTIONAL	-- Need ON
	]],
	[[	cqi-ReportAperiodicProc-r13		CQI-ReportAperiodicProc-r13		OPTIONAL,		-- Need ON
		cqi-ReportAperiodicProc2-r13		CHOICE {
			release						NULL,
			setup						CQI-ReportAperiodicProc-r13
		}														OPTIONAL,		-- Need ON
		eMIMO-Type-r13				CHOICE {
			release						NULL,
			setup						CHOICE {
				nonPrecoded-r13				CSI-RS-InfoNonPrecoded-r13,
				beamformed-r13				CSI-RS-InfoBeamformed-r13
			}
		}														OPTIONAL	-- Need ON
	]]
}

P-C-AndCBSR-r11 ::=	SEQUENCE {
	p-C-r11						INTEGER (-8..15),
	codebookSubsetRestriction-r11	BIT STRING
}

P-C-AndCBSR-r13 ::=	SEQUENCE {
	legacySet						SEQUENCE {
		p-C-r11						INTEGER (-8..15),
		codebookSubsetRestriction1-r13	BIT STRING
	}												OPTIONAL,	-- Cond BeamformedKna
	codebookSubsetRestriction2-r13	BIT STRING		OPTIONAL,	-- Cond NonPreCoded
	codebookSubsetRestriction3-r13	BIT STRING		OPTIONAL	-- Cond BeamformedK1a
}

P-C-AndCBSR-PerResourceConfig-r13 ::=	SEQUENCE (SIZE (1..2)) OF P-C-AndCBSR-r13

-- ASN1STOP

CSI-Process field descriptions
alternativeCodebookEnabledFor4TXProc
Indicates whether code book in TS 36.213 [23] Table 7.2.4-0A to Table 7.2.4-0D is being used for deriving CSI feedback and reporting for a CSI process. EUTRAN may configure the field only if the number of CSI-RS ports for non-zero power transmission CSI-RS configuration is 4.
codebookSubsetRestriction
Parameter: codebookSubsetRestriction, see TS 36.213 [23] and TS 36.211 [21]. The number of bits in the codebookSubsetRestriction for applicable transmission modes is defined in TS 36.213 [23].
codebookSubsetRestriction2List
If p-C-AndCBSRList-r13 is included, E-UTRAN includes 2 entries otherwise 1 (i.e. E-UTRAN configures the same number of entries for the original and the CBSR2 field.
codebookSubsetRestriction3
E-UTRAN configures the field only if neither p-C-AndCBSRListExt nor alternativeCodebookEnabledBeamformed is not configured.
cqi-ReportAperiodicProc
If csi-MeasSubframeSets-r12 is configured for the same frequency as the CSI process, cqi-ReportAperiodicProc
applies for CSI subframe set 1. If csi-MeasSubframeSet1-r10 or csi-MeasSubframeSet2-r10 are configured for the same frequency as the CSI process, cqi-ReportAperiodicProc applies for CSI subframe set 1 or CSI subframe set 2. Otherwise, cqi-ReportAperiodicProc applies for all subframes
cqi-ReportAperiodicProc2
cqi-ReportAperiodicProc2 is configured only if csi-MeasSubframeSets-r12 is configured for the same frequency as the CSI process. cqi-ReportAperiodicProc2 is for CSI subframe set 2. E-UTRAN shall set cqi-ReportModeAperiodic-r11 in cqi-ReportAperiodicProc2 the same as in cqi-ReportAperiodicProc.
cqi-ReportBothProc
Includes CQI configuration parameters applicable for both aperiodic and periodic CSI reporting, for which CSI process specific values may be configured. E-UTRAN configures the field if and only if cqi-ReportPeriodicProcId is included and/ or if cqi-ReportAperiodicProc is included.
cqi-ReportPeriodicProcId
Refers to a periodic CQI reporting configuration that is configured for the same frequency as the CSI process. Value 0 refers to the set of parameters defined by the REL-10 CQI reporting configuration fields, while the other values refer to the additional configurations E-UTRAN assigns by CQI-ReportPeriodicProcExt-r11 (and as covered by CQI-ReportPeriodicProcExtId).
csi-IM-ConfigId
Refers to a CSI-IM configuration that is configured for the same frequency as the CSI process.
csi-IM-ConfigIdList 
 Refers to one or two CSI-IM configurations that are configured for the same frequency as the CSI process. csi-IM-ConfigIdList can include 2 entries only if csi-MeasSubframeSets-r12 is configured for the same frequency as the CSI process. UE shall ignore csi-IM-ConfigId-r11 if csi-IM-ConfigIdList-r12 is configured.
csi-RS-ConfigNZPId
Refers to a CSI RS configuration using non-zero power transmission that is configured for the same frequency as the CSI process.
p-C
Parameter: , see TS 36.213 [23, 7.2.5].
p-C-AndCBSRList
A p-C-AndCBSRList including 2 entries indicates that the subframe patterns configured for CSI (CQI/PMI/PTI/RI) reporting (i.e. as defined by field csi-MeasSubframeSet1 and csi-MeasSubframeSet2, or as defined by csi-MeasSubframeSets-r12) are to be used for this CSI process, while a single entry indicates that the subframe patterns are not to be used for this CSI process. E-UTRAN does not include 2 entries in p-C-AndCBSRList with csi-MeasSubframeSet1 and csi-MeasSubframeSet2 for CSI processes concerning a secondary frequency. E-UTRAN includes 2 entries in p-C-AndCBSRList when configuring both cqi-pmi-ConfigIndex and cqi-pmi-ConfigIndex2. If included in CSI-RS-InfoBeamformed within CSI-RS-Config (i.e. TM9), E-UTRAN configures a single entry.

Conditional presence
Explanation
BeamformedK1a
The field is optionally present, need OR, if included in CSI-RS-InfoBeamformed while neither csi-RS-ConfigNZPIdListExt nor alternativeCodebookEnabledBeamformed is configured. Otherwise the field is not present
BeamformedKna
The field is optionally present, need OR, if included in CSI-RS-InfoBeamformed while csi-RS-ConfigNZPIdListExt is configured but alternativeCodebookEnabledBeamformed is not. Otherwise the field is not present
NonPreCoded
The field is optionally present, need OR, if included in CSI-RS-InfoNonPrecoded. Otherwise the field is not present

-	CSI-ProcessId
The IE CSI-ProcessId is used to identify a CSI process that is configured by the IE CSI-Process. The identity is unique within the scope of a carrier frequency.
CSI-ProcessId information elements
-- ASN1START

CSI-ProcessId-r11 ::=		INTEGER (1..maxCSI-Proc-r11)

-- ASN1STOP

-	CSI-RS-Config
The IE CSI-RS-Config is used to specify the CSI (Channel-State Information) reference signal configuration.
CSI-RS-Config information elements
-- ASN1START

CSI-RS-Config-r10 ::=		SEQUENCE {
	csi-RS-r10					CHOICE {
		release						NULL,
		setup						SEQUENCE {
			antennaPortsCount-r10			ENUMERATED {an1, an2, an4, an8},
			resourceConfig-r10				INTEGER (0..31),
			subframeConfig-r10				INTEGER (0..154),
			p-C-r10							INTEGER (-8..15)
		}
	}																OPTIONAL,			-- Need ON
	zeroTxPowerCSI-RS-r10		ZeroTxPowerCSI-RS-Conf-r12			OPTIONAL			-- Need ON
}

CSI-RS-Config-v1250 ::=		SEQUENCE {
	zeroTxPowerCSI-RS2-r12		ZeroTxPowerCSI-RS-Conf-r12			OPTIONAL,			-- Need ON
	ds-ZeroTxPowerCSI-RS-r12		CHOICE {
		release							NULL,
		setup							SEQUENCE {
			zeroTxPowerCSI-RS-List-r12		SEQUENCE (SIZE (1..maxDS-ZTP-CSI-RS-r12)) OF ZeroTxPowerCSI-RS-r12
		}
	}																OPTIONAL				-- Need ON
}

CSI-RS-Config-v13x0 ::=		SEQUENCE {
	eMIMO-Type-r13				CHOICE {
		release						NULL,
		setup						CHOICE {
			nonPrecoded-r13				CSI-RS-InfoNonPrecoded-r13,
			beamformed-r13				CSI-RS-InfoBeamformed-r13
		}
	}														OPTIONAL	-- Need ON
}

ZeroTxPowerCSI-RS-Conf-r12 ::=	CHOICE {
		release							NULL,
		setup							ZeroTxPowerCSI-RS-r12 
}

ZeroTxPowerCSI-RS-r12 ::=	SEQUENCE {
	zeroTxPowerResourceConfigList-r12		BIT STRING (SIZE (16)),
	zeroTxPowerSubframeConfig-r12			INTEGER (0..154)
}

-- ASN1STOP

CSI-RS-Config field descriptions
antennaPortsCount
Parameter represents the number of antenna ports used for transmission of CSI reference signals where value an1 corresponds to 1 antenna port, an2 to 2 antenna ports and so on, see TS 36.211 [21, 6.10.5].
ds-ZeroTxPowerCSI-RS
Parameter for additional zeroTxPowerCSI-RS for a serving cell, concerning the CSI-RS included in discovery signals.
zeroTxPowerCSI-RS2
Parameter for additional zeroTxPowerCSI-RS for a serving cell. E-UTRAN configures the field only if csi-MeasSubframeSets-r12 and TM 1 - 9 are configured for the serving cell.
p-C
Parameter: , see TS 36.213 [23, 7.2.5].
resourceConfig
Parameter: CSI reference signal configuration, see TS 36.211 [21, table 6.10.5.2-1 and 6.10.5.2-2].
subframeConfig
Parameter: , see TS 36.211 [21, table 6.10.5.3-1].
zeroTxPowerResourceConfigList
Parameter: ZeroPowerCSI-RS, see TS 36.213 [23, 7.2.7].
zeroTxPowerSubframeConfig
Parameter: , see TS 36.211 [21, table 6.10.5.3-1].

-	CSI-RS-ConfigNZP
The IE CSI-RS-ConfigNZP is the CSI-RS resource configuration using non-zero power transmission that E-UTRAN may configure on a serving frequency.
CSI-RS-ConfigNZP information elements
-- ASN1START

CSI-RS-ConfigNZP-r11 ::=		SEQUENCE {
	csi-RS-ConfigNZPId-r11			CSI-RS-ConfigNZPId-r11,
	antennaPortsCount-r11			ENUMERATED {an1, an2, an4, an8},
	resourceConfig-r11				INTEGER (0..31),
	subframeConfig-r11				INTEGER (0..154),
	scramblingIdentity-r11			INTEGER (0..503),
	qcl-CRS-Info-r11				SEQUENCE {
		qcl-ScramblingIdentity-r11		INTEGER (0..503),
		crs-PortsCount-r11				ENUMERATED {n1, n2, n4, spare1},
		mbsfn-SubframeConfigList-r11	CHOICE {
				release						NULL,
				setup						SEQUENCE {
					subframeConfigList			MBSFN-SubframeConfigList
				}
		}																OPTIONAL	-- Need ON
	}																	OPTIONAL,	-- Need OR
	...,
	[[	eMIMO-Info-r13					CHOICE {
			release						NULL,
			setup						SEQUENCE {
				nzp-resourceConfigList-r13		SEQUENCE (SIZE (2..8)) OF ResourceConfig-r13,
				cdmType							ENUMERATED {cdm2, cdm4}	OPTIONAL	-- Need OR
			}
		}																OPTIONAL	-- Need ON
	]]
}

ResourceConfig-r13 ::=				INTEGER (0..31)

-- ASN1STOP

CSI-RS-ConfigNZP field descriptions
antennaPortsCount
Parameter represents the number of antenna ports used for transmission of CSI reference signals where an1 corresponds to 1, an2 to 2 antenna ports etc. see TS 36.211 [21, 6.10.5].
cdmType
EUTRAN configures this field only for CSI processes that include eMIMO-Type set to nonPrecoded.
qcl-CRS-Info
Indicates CRS antenna ports that is quasi co-located with the CSI-RS antenna ports, see TS 36.213 [23, 7.2.5]. EUTRAN configures this field if and only if the UE is configured with qcl-Operation set to typeB.
resourceConfig
Parameter: CSI reference signal configuration, see TS 36.211 [21, table 6.10.5.2-1 and 6.10.5.2-2].
subframeConfig
Parameter: , see TS 36.211 [21, table 6.10.5.3-1].
scramblingIdentity
Parameter: Pseudo-random sequence generator parameter, , see TS 36.213 [23, 7.2.5].

-	CSI-RS-ConfigNZPId
The IE CSI-RS-ConfigNZPId is used to identify a CSI-RS resource configuration using non-zero transmission power, as configured by the IE CSI-RS-ConfigNZP. The identity is unique within the scope of a carrier frequency.
CSI-RS-ConfigNZPId information elements
-- ASN1START

CSI-RS-ConfigNZPId-r11 ::=					INTEGER (1..maxCSI-RS-NZP-r11)

-- ASN1STOP

-	CSI-RS-ConfigZP
The IE CSI-RS-ConfigZP is the CSI-RS resource configuration, for which UE assumes zero transmission power, that E-UTRAN may configure on a serving frequency.
CSI-RS-ConfigZP information elements
-- ASN1START

CSI-RS-ConfigZP-r11 ::=		SEQUENCE {
	csi-RS-ConfigZPId-r11		CSI-RS-ConfigZPId-r11,
	resourceConfigList-r11		BIT STRING (SIZE (16)),
	subframeConfig-r11			INTEGER (0..154),
	...
}

-- ASN1STOP

CSI-RS-ConfigZP field descriptions
resourceConfigList
Parameter: ZeroPowerCSI-RS, see TS 36.213 [23, 7.2.7].
subframeConfig
Parameter: , see TS 36.211 [21, table 6.10.5.3-1].

-	CSI-RS-ConfigZPId
The IE CSI-RS-ConfigZPId is used to identify a CSI-RS resource configuration for which UE assumes zero transmission power, as configured by the IE CSI-RS-ConfigZP. The identity is unique within the scope of a carrier frequency.
CSI-RS-ConfigZPId information elements
-- ASN1START

CSI-RS-ConfigZPId-r11 ::=					INTEGER (1..maxCSI-RS-ZP-r11)

-- ASN1STOP

-	CSI-RS-Info
The IE CSI-RS-Info is used to specify CSI-RS related configuration information.
CSI-RS-Info information elements
-- ASN1START

CSI-RS-InfoNonPrecoded-r13 ::=			SEQUENCE {
	p-C-AndCBSRList-r13						SEQUENCE (SIZE (1..2)) OF P-C-AndCBSR-r13	OPTIONAL,	-- Need OR
	codebookConfigN1-r13					ENUMERATED {an1, an2, an3, an4, an8},
	codebookConfigN2-r13					ENUMERATED {an1, an2, an3, an4, an8},
	codebookOverSamplingRateConfig-O1-r13	ENUMERATED {na,an4,an8},
	codebookOverSamplingRateConfig-O2-r13	ENUMERATED {na,an4,an8},
	codebookConfig-r13						ENUMERATED {an1, an2, an3, an4},
	interferenceMeasRestriction-r13			ENUMERATED {on}			OPTIONAL	-- Need OR
}

CSI-RS-InfoBeamformed-r13::=			SEQUENCE	{
	csi-RS-ConfigNZPIdListExt-r13 			SEQUENCE (SIZE (1..7)) OF CSI-RS-ConfigNZPId-r11	OPTIONAL,	-- Need OR
	csi-IM-ConfigIdListExt-r13				SEQUENCE (SIZE (1..7)) OF CSI-IM-ConfigIdInfo-r13	OPTIONAL,	-- Need OR
	p-C-AndCBSR-PerResourceConfigList-r13	SEQUENCE (SIZE (1..7)) OF P-C-AndCBSR-PerResourceConfig-r13	OPTIONAL,	-- Need OR
	alternativeCodebookEnabledBeamformed-r13	ENUMERATED {true}	OPTIONAL,	-- Need OR
	channelMeasRestriction-r13				ENUMERATED {on}			OPTIONAL	-- Need OR
}

CSI-IM-ConfigIdInfo-r13 ::=	SEQUENCE {
	csi-IM-ConfigId-r13					CSI-IM-ConfigId-r11		OPTIONAL,
	interferenceMeasRestriction-r13			ENUMERATED {on} 		OPTIONAL	-- Need OR
}

-- ASN1STOP

CSI-RS-Info field descriptions
alternativeCodebookEnabledBeamformed
If included in CSI-Process (i.e. TM10), the field indicates whether code book in TS 36.213 [23] Table 7.2.4-9 to Table 7.2.4-20 is being used for deriving CSI feedback and reporting for a CSI process. EUTRAN configures the field only for a process referring to a single RS configuration using non-zero power transmission (i.e a process for which csi-RS-ConfigNZPIdListExt is not configured).
codebookConfigN1
Indicates the number of antenna ports per polarization in dimension x as used for transmission of CSI reference signals. Value an1 corresponds to 1 antenna port, an2 to 2 antenna ports and so on, see TS 36.213 [23].
codebookOverSamplingRateConfig-Ox
Indicates the spatial over-sampling rate in dimension x as used for transmission of CSI reference signals. Value an1 corresponds to 1 antenna port, an2 to 2 antenna ports and so on, see TS 36.213 [23].
CSI-RS-InfoBeamformed
E-UTRAN configures field csi-IM-ConfigIdListExt only if the IE is included in CSI-Process (i.e. when TM10 is configured for the serving cell).
interferenceMeasRestriction
E-UTRAN configures the field only if csi-IM-ConfigIdList is configured (i.e. with TM10).


-	DMRS-Config
The IE DMRS-Config is the DMRS configuration that E-UTRAN may configure on a serving frequency. 
DMRS-Config information elements
-- ASN1START

DMRS-Config-r11 ::=		CHOICE {
	release						NULL,
	setup						SEQUENCE {
		scramblingIdentity-r11		INTEGER (0..503),
		scramblingIdentity2-r11		INTEGER (0..503)
	}
}
DMRS-Config-v13x0 ::=			SEQUENCE {
		dmrs-tableAlt-r13				ENUMERATED {true}			OPTIONAL	-- Need OR
}

-- ASN1STOP

DMRS-Config field descriptions
scramblingIdentity, scramblingIdentity2
Parameter: , see TS 36.211 [21, 6.10.3.1].
dmrs-tableAlt
The field indicates whether or not to use an alternative table for DMRS upon PDSCH transmission, see TS 36.213 [23].

-	DRB-Identity
The IE DRB-Identity is used to identify a DRB used by a UE.
DRB-Identity information elements
-- ASN1START

DRB-Identity ::=					INTEGER (1..32)

-- ASN1STOP

-	EPDCCH-Config
The IE EPDCCH-Config specifies the subframes and resource blocks for EPDCCH monitoring that E-UTRAN may configure for a serving cell.
EPDCCH-Config information element
-- ASN1START

EPDCCH-Config-r11 ::=		SEQUENCE{
	config-r11		CHOICE {
		release						NULL,
			setup						SEQUENCE {
			subframePatternConfig-r11	CHOICE {
				release						NULL,
				setup						SEQUENCE {
					subframePattern-r11			MeasSubframePattern-r10
				}
			}																	OPTIONAL, -- Need ON
			startSymbol-r11				INTEGER (1..4)							OPTIONAL, -- Need OP
			setConfigToReleaseList-r11	EPDCCH-SetConfigToReleaseList-r11		OPTIONAL, -- Need ON
			setConfigToAddModList-r11	EPDCCH-SetConfigToAddModList-r11		OPTIONAL -- Need ON
		}
	}
}

EPDCCH-SetConfigToAddModList-r11 ::=	SEQUENCE (SIZE(1..maxEPDCCH-Set-r11)) OF EPDCCH-SetConfig-r11

EPDCCH-SetConfigToReleaseList-r11 ::=	SEQUENCE (SIZE(1..maxEPDCCH-Set-r11)) OF EPDCCH-SetConfigId-r11

EPDCCH-SetConfig-r11 ::=		SEQUENCE {
	setConfigId-r11					EPDCCH-SetConfigId-r11,
	transmissionType-r11			ENUMERATED {localised, distributed},
	resourceBlockAssignment-r11		SEQUENCE{
		numberPRB-Pairs-r11				ENUMERATED {n2, n4, n8},
		resourceBlockAssignment-r11		BIT STRING (SIZE(4..38))
	},
	dmrs-ScramblingSequenceInt-r11	INTEGER (0..503),
	pucch-ResourceStartOffset-r11	INTEGER (0..2047),
	re-MappingQCL-ConfigId-r11		PDSCH-RE-MappingQCL-ConfigId-r11	OPTIONAL, -- Need OR
	...,
	[[	csi-RS-ConfigZPId2-r12				CHOICE {
			release						NULL,
			setup						CSI-RS-ConfigZPId-r11
		}															OPTIONAL	-- Need ON
	]]
}

EPDCCH-SetConfigId-r11 ::=	INTEGER (0..1)

-- ASN1STOP

EPDCCH-Config field descriptions
csi-RS-ConfigZPId2
Indicates the rate matching parameters in addition to those indicated by re-MappingQCL-ConfigId. E-UTRAN configures this field only when tm10 is configured.
dmrs-ScramblingSequenceInt
The DMRS scrambling sequence initialization parameter  defined in TS 36.211[21, 6.10.3A.1].
EPDCCH-SetConfig
Provides EPDCCH configuration set. See TS 36.213 [23, 9.1.4]. E-UTRAN configures at least one EPDCCH-SetConfig when EPDCCH-Config is configured.
numberPRB-Pairs
Indicates the number of physical resource-block pairs used for the EPDCCH set. Value n2 corresponds to 2 physical resource-block pairs; n4 corresponds to 4 physical resource-block pairs and so on. Value n8 is not supported if dl-Bandwidth is set to 6 resource blocks.
pucch-ResourceStartOffset
PUCCH format 1a, 1b and 3 resource starting offset for the EPDCCH set. See TS 36.213 [23, 10.1].
re-MappingQCL-ConfigId
Indicates the starting OFDM symbol, the related rate matching parameters and quasi co-location assumption for EPDCCH when the UE is configured with tm10. This field provides the identity of a configured PDSCH-RE-MappingQCL-Config. E-UTRAN configures this field only when tm10 is configured.
resourceBlockAssignment
Indicates the index to a specific combination of physical resource-block pair for EPDCCH set. See TS 36.213 [23, 9.1.4.4]. The size of resourceBlockAssignment is specified in TS 36.213 [23, 9.1.4.4] and based on numberPRB-Pairs and the signalled value of dl-Bandwidth.
setConfigId
Indicates the identity of the EPDCCH configuration set.
startSymbol 
Indicates the OFDM starting symbol for any EPDCCH and PDSCH scheduled by EPDCCH on the same cell, see TS 36.213 [23, 9.1.4.1]. If not present, the UE shall release the configuration and shall derive the starting OFDM symbol of EPDCCH and PDSCH scheduled by EPDCCH from PCFICH. Values 1, 2, and 3 are applicable for dl-Bandwidth greater than 10 resource blocks. Values 2, 3, and 4 are applicable otherwise. E-UTRAN does not configure the field for UEs configured with tm10.
subframePatternConfig 
Configures the subframes which the UE shall monitor the UE-specific search space on EPDCCH, except for pre-defined rules in TS 36.213 [23, 9.1.4]. If the field is not configured when EPDCCH is configured, the UE shall monitor the UE-specific search space on EPDCCH in all subframes except for pre-defined rules in TS 36.213 [23, 9.1.4].
transmissionType
Indicates whether distributed or localized EPDCCH transmission mode is used as defined in TS 36.211 [21, 6.8A.1].

-	EIMTA-MainConfig
The IE EIMTA-MainConfig is used to specify the eIMTA-RNTI used for eIMTA and the subframes used for monitoring PDCCH with eIMTA-RNTI. The IE EIMTA-MainConfigServCell is used to specify the eIMTA related parameters applicable for the concerned serving cell.
EIMTA-MainConfig information element
-- ASN1START
EIMTA-MainConfig-r12 ::=	CHOICE {
	release							NULL,
	setup							SEQUENCE {
		eimta-RNTI-r12				C-RNTI,
		eimta-CommandPeriodicity-r12	ENUMERATED {sf10, sf20, sf40, sf80},
		eimta-CommandSubframeSet-r12	BIT STRING (SIZE(10))
	}
}

EIMTA-MainConfigServCell-r12 ::=	CHOICE {
	release								NULL,
	setup								SEQUENCE {
		eimta-UL-DL-ConfigIndex-r12				INTEGER (1..5),
		eimta-HARQ-ReferenceConfig-r12		ENUMERATED {sa2,sa4,sa5},
		mbsfn-SubframeConfigList-v1250		CHOICE {
				release								NULL,
				setup								SEQUENCE {
				subframeConfigList-r12				MBSFN-SubframeConfigList
				}
		}
	}
}

-- ASN1STOP

EIMTA-MainConfig field descriptions
eimta-CommandPeriodicity
Configures the periodicity to monitor PDCCH with eIMTA-RNTI, see TS 36.213 [23, 13.1]. Value sf10 corresponds to 10 subframes, sf20 corresponds to 20 subframes and so on.
eimta-CommandSubframeSet
Configures the subframe(s) to monitor PDCCH with eIMTA-RNTI within the periodicity configured by eimta-CommandPeriodicity. The 10 bits correspond to all subframes in the last radio frame within each periodicity. The left most bit is for subframe 0 and so on. Each bit can be of value 0 or 1. The value of 1 means that the corresponding subframe is configured for monitoring PDCCH with eIMTA-RNTI, and the value of 0 means otherwise. In case of TDD as PCell, only the downlink subframes indicated by the UL/ DL configuration in SIB1 can be configured for monitoring PDCCH with eIMTA-RNTI. In case of FDD as PCell, any of the ten subframes can be configured for monitoring PDCCH with eIMTA-RNTI.
eimta-HARQ-ReferenceConfig 
Indicates UL/ DL configuration used as the DL HARQ reference configuration for this serving cell. Value sa2 corresponds to Configuration2, sa4 to Configuration4 etc, as specified in TS 36.211 [21, table 4.2-2]. E-UTRAN configures the same value for all serving cells residing on same frequency band.
eimta-UL-DL-ConfigIndex
Index of I, see TS 36.212 [22, 5.3.3.1.4]. E-UTRAN configures the same value for all serving cells residing on same frequency band.
mbsfn-SubframeConfigList
Configure the MBSFN subframes for the UE on this serving cell. An uplink subframe indicated by the DL/UL subframe configuration in SIB1 can be configured as MBSFN subframe.

-	LogicalChannelConfig
The IE LogicalChannelConfig is used to configure the logical channel parameters.
LogicalChannelConfig information element
-- ASN1START

LogicalChannelConfig ::=			SEQUENCE {
	ul-SpecificParameters				SEQUENCE {
		priority							INTEGER (1..16),
		prioritisedBitRate					ENUMERATED {
												kBps0, kBps8, kBps16, kBps32, kBps64, kBps128,
												kBps256, infinity, kBps512-v1020, kBps1024-v1020,
												kBps2048-v1020, spare5, spare4, spare3, spare2,
												spare1},
		bucketSizeDuration					ENUMERATED {
												ms50, ms100, ms150, ms300, ms500, ms1000, spare2,
												spare1},
		logicalChannelGroup					INTEGER (0..3)			OPTIONAL			-- Need OR
	}		OPTIONAL,																	-- Cond UL
	...,
	[[	logicalChannelSR-Mask-r9			ENUMERATED {setup}		OPTIONAL		-- Cond SRmask
	]],
	[[	logicalChannelSR-Prohibit-r12		BOOLEAN					OPTIONAL		-- Need ON
	]]
}

-- ASN1STOP

LogicalChannelConfig field descriptions
bucketSizeDuration
Bucket Size Duration for logical channel prioritization in TS 36.321 [6]. Value in milliseconds. Value ms50 corresponds to 50 ms, ms100 corresponds to 100 ms and so on.
logicalChannelGroup
Mapping of logical channel to logical channel group for BSR reporting in TS 36.321 [6].
logicalChannelSR-Mask
Controlling SR triggering on a logical channel basis when an uplink grant is configured. See TS 36.321 [6].
logicalChannelSR-Prohibit
Value TRUE indicates that the logicalChannelSR-ProhibitTimer is enabled for the logical channel. E-UTRAN only (optionally) configures the field (i.e. indicates value TRUE) if logicalChannelSR-ProhibitTimer is configured. See TS 36.321 [6].
prioritisedBitRate
Prioritized Bit Rate for logical channel prioritization in TS 36.321 [6]. Value in kilobytes/second. Value kBps0 corresponds to 0 kB/second, kBps8 corresponds to 8 kB/second, kBps16 corresponds to 16 kB/second and so on. Infinity is the only applicable value for SRB1 and SRB2
priority
Logical channel priority in TS 36.321 [6]. Value is an integer.

Conditional presence
Explanation
SRmask
The field is optionally present if ul-SpecificParameters is present, need OR; otherwise it is not present.
UL
The field is mandatory present for UL logical channels; otherwise it is not present.

-	MAC-MainConfig
The IE MAC-MainConfig is used to specify the MAC main configuration for signalling and data radio bearers. All MAC main configuration parameters can be configured independently per Cell Group (i.e. MCG or SCG), unless explicitly specified otherwise.
MAC-MainConfig information element
-- ASN1START

MAC-MainConfig ::=					SEQUENCE {
	ul-SCH-Config						SEQUENCE {
		maxHARQ-Tx							ENUMERATED {
												n1, n2, n3, n4, n5, n6, n7, n8,
												n10, n12, n16, n20, n24, n28,
												spare2, spare1}		OPTIONAL,	-- Need ON
		periodicBSR-Timer					PeriodicBSR-Timer-r12	OPTIONAL,	-- Need ON
		retxBSR-Timer						RetxBSR-Timer-r12,
		ttiBundling							BOOLEAN
	}																OPTIONAL, 	-- Need ON
	drx-Config							DRX-Config					OPTIONAL,	-- Need ON
	timeAlignmentTimerDedicated			TimeAlignmentTimer,
	phr-Config							CHOICE {
		release								NULL,
		setup								SEQUENCE {
			periodicPHR-Timer					ENUMERATED {sf10, sf20, sf50, sf100, sf200,
															sf500, sf1000, infinity},
			prohibitPHR-Timer					ENUMERATED {sf0, sf10, sf20, sf50, sf100,
																sf200, sf500, sf1000},
			dl-PathlossChange					ENUMERATED {dB1, dB3, dB6, infinity}
		}
	}																OPTIONAL,	-- Need ON
	...,
	[[	sr-ProhibitTimer-r9					INTEGER (0..7)			OPTIONAL	-- Need ON
	]],
	[[	mac-MainConfig-v1020				SEQUENCE {
			sCellDeactivationTimer-r10			ENUMERATED {
													rf2, rf4, rf8, rf16, rf32, rf64, rf128,
													spare}			OPTIONAL,	-- Need OP
			extendedBSR-Sizes-r10				ENUMERATED {setup}		OPTIONAL,	-- Need OR
			extendedPHR-r10						ENUMERATED {setup}		OPTIONAL	-- Need OR
		}															OPTIONAL	-- Need ON
	]],
	[[	stag-ToReleaseList-r11				STAG-ToReleaseList-r11	OPTIONAL,	-- Need ON
		stag-ToAddModList-r11				STAG-ToAddModList-r11	OPTIONAL,	-- Need ON
		drx-Config-v1130					DRX-Config-v1130		OPTIONAL	-- Need ON
	]],
	[[	e-HARQ-Pattern-r12					BOOLEAN					OPTIONAL,	-- Need ON
		dualConnectivityPHR					CHOICE {
			release								NULL,
			setup								SEQUENCE {
				phr-ModeOtherCG-r12					ENUMERATED {real, virtual}
			}
		}														OPTIONAL,	-- Need ON
		logicalChannelSR-Config-r12		CHOICE {
			release								NULL,
			setup								SEQUENCE {
				logicalChannelSR-ProhibitTimer-r12		ENUMERATED {sf20, sf40, sf64, sf128, sf512, sf1024, sf2560, spare1}
			}
		}															OPTIONAL		-- Need ON
	]],
	[[	extendedPHR2-r13					ENUMERATED {setup}		OPTIONAL,		-- Need ON 
		eDRX-Config-CycleStartOffset-r13 	CHOICE {
			release							NULL,
			setup
											CHOICE {
			sf5120									INTEGER(0..1),
			sf10240									INTEGER(0..3)
			}
		}										OPTIONAL	-- Need ON
	]]
}

MAC-MainConfigSCell-r11 ::=			SEQUENCE {
	stag-Id-r11							STAG-Id-r11		OPTIONAL,	-- Need OP
	...
}

DRX-Config ::=						CHOICE {
	release								NULL,
	setup								SEQUENCE {
		onDurationTimer						ENUMERATED {
												psf1, psf2, psf3, psf4, psf5, psf6,
												psf8, psf10, psf20, psf30, psf40,
												psf50, psf60, psf80, psf100,
												psf200},
		drx-InactivityTimer					ENUMERATED {
												psf1, psf2, psf3, psf4, psf5, psf6,
												psf8, psf10, psf20, psf30, psf40,
												psf50, psf60, psf80, psf100,
												psf200, psf300, psf500, psf750,
												psf1280, psf1920, psf2560, psf0-v1020,
												spare9, spare8, spare7, spare6,
												spare5, spare4, spare3, spare2,
												spare1},
		drx-RetransmissionTimer				ENUMERATED {
												psf1, psf2, psf4, psf6, psf8, psf16,
												psf24, psf33},
		longDRX-CycleStartOffset		CHOICE {
			sf10							INTEGER(0..9),
			sf20							INTEGER(0..19),
			sf32							INTEGER(0..31),
			sf40							INTEGER(0..39),
			sf64							INTEGER(0..63),
			sf80							INTEGER(0..79),
			sf128							INTEGER(0..127),
			sf160							INTEGER(0..159),
			sf256							INTEGER(0..255),
			sf320							INTEGER(0..319),
			sf512							INTEGER(0..511),
			sf640							INTEGER(0..639),
			sf1024							INTEGER(0..1023),
			sf1280							INTEGER(0..1279),
			sf2048							INTEGER(0..2047),
			sf2560							INTEGER(0..2559)
		},
		shortDRX							SEQUENCE {
			shortDRX-Cycle						ENUMERATED	{
													sf2, sf5, sf8, sf10, sf16, sf20,
													sf32, sf40, sf64, sf80, sf128, sf160,
													sf256, sf320, sf512, sf640},
			drxShortCycleTimer					INTEGER (1..16)
		}		OPTIONAL													-- Need OR
	}
}

DRX-Config-v1130 ::=					SEQUENCE {
	drx-RetransmissionTimer-v1130			ENUMERATED {psf0-v1130}	OPTIONAL,	--Need OR
	longDRX-CycleStartOffset-v1130			CHOICE {
		sf60-v1130								INTEGER(0..59),
		sf70-v1130								INTEGER(0..69)
	}																OPTIONAL,	--Need OR
	shortDRX-Cycle-v1130					ENUMERATED	{sf4-v1130}	OPTIONAL	--Need OR
}

PeriodicBSR-Timer-r12 ::=					ENUMERATED {
												sf5, sf10, sf16, sf20, sf32, sf40, sf64, sf80,
												sf128, sf160, sf320, sf640, sf1280, sf2560,
												infinity, spare1}

RetxBSR-Timer-r12 ::=							ENUMERATED {
												sf320, sf640, sf1280, sf2560, sf5120,
												sf10240, spare2, spare1}

STAG-ToReleaseList-r11 ::=	SEQUENCE (SIZE (1..maxSTAG-r11)) OF STAG-Id-r11

STAG-ToAddModList-r11 ::=	SEQUENCE (SIZE (1..maxSTAG-r11)) OF STAG-ToAddMod-r11

STAG-ToAddMod-r11 ::=		SEQUENCE {
	stag-Id-r11					STAG-Id-r11,
	timeAlignmentTimerSTAG-r11	TimeAlignmentTimer,
	...
}

STAG-Id-r11::=				INTEGER (1..maxSTAG-r11)

-- ASN1STOP

MAC-MainConfig field descriptions
dl-PathlossChange
DL Pathloss Change and the change of the required power backoff due to power management (as allowed by P-MPRc [42]) for PHR reporting in TS 36.321 [6]. Value in dB. Value dB1 corresponds to 1 dB, dB3 corresponds to 3 dB and so on. The same value applies for each serving cell (although the associated functionality is performed independently for each cell).
drx-Config
Used to configure DRX as specified in TS 36.321 [6]. E-UTRAN configures the values in DRX-Config-v1130 only if the UE indicates support for IDC indication. E-UTRAN configures drx-Config-v1130 only if drx-Config (without suffix) is configured.
drx-InactivityTimer
Timer for DRX in TS 36.321 [6]. Value in number of PDCCH sub-frames. Value psf1 corresponds to 1 PDCCH sub-frame, psf2 corresponds to 2 PDCCH sub-frames and so on.
drx-RetransmissionTimer
Timer for DRX in TS 36.321 [6]. Value in number of PDCCH sub-frames. Value psf1 corresponds to 1 PDCCH sub-frame, psf2 corresponds to 2 PDCCH sub-frames and so on. In case drx-RetransmissionTimer-v1130 is signalled, the UE shall ignore drx-RetransmissionTimer (i.e. without suffix).
drxShortCycleTimer
Timer for DRX in TS 36.321 [6]. Value in multiples of shortDRX-Cycle. A value of 1 corresponds to shortDRX-Cycle, a value of 2 corresponds to 2 * shortDRX-Cycle and so on.
dualConnectivityPHR
Indicates if power headroom shall be reported using Dual Connectivity Power Headroom Report MAC Control Element defined in TS 36.321 [6] (value setup). If PHR functionality and dual connectivity are configured, E-UTRAN always configures the value setup for this field and configures phr-Config and dualConnectivityPHR for both CGs.
e-HARQ-Pattern
TRUE indicates that enhanced HARQ pattern for TTI bundling is enabled for FDD. E-UTRAN enables this field only when ttiBundling is set to TRUE.
eDRX-Config-CycleStartOffset
Indicates longDRX-Cycle and drxStartOffset in TS 36.321 [6]. The value of longDRX-Cycle is in number of sub-frames. The value of drxStartOffset, in number of subframes, is indicated by the value of eDRX-Config-CycleStartOffset multiplied by 2560 plus the offset value configured in longDRX-CycleStartOffset. E-UTRAN only configures value setup when the value in longDRX-CycleStartOffset is sf2560.
extendedBSR-Sizes
If value setup is configured, the BSR index indicates extended BSR size levels as defined in TS 36.321 [6, Table 6.1.3.1-2].
extendedPHR
Indicates if power headroom shall be reported using the Extended Power Headroom Report MAC control element defined in TS 36.321 [6] (value setup). E-UTRAN always configures the value setup if more than one and up to eight Serving Cell(s) with uplink is configured and none of the serving cells with uplink configured has a servingCellIndex higher than seven and if PUCCH on SCell is not configured and if dual connectivity is not configured. E-UTRAN configures extendedPHR only if phr-Config is configured. The UE shall release extendedPHR if phr-Config is released.
extendedPHR2
Indicates if power headroom shall be reported using the Extended Power Headeroom Report 2 MAC Control Element defined in TS 36.321 [6] (value setup). E-UTRAN always configures the value setup if any of the serving cells with uplink configured has a servingCellIndex higher than seven or if PUCCH SCell (with any number of serving cells with uplink configured) is configured. E-UTRAN configures extendedPHR2 only if phr-Config is configured. The UE shall release extendedPHR2 if phr-Config is released.
logicalChannelSR-ProhibitTimer
Timer used to delay the transmission of an SR for logical channels enabled by logicalChannelSR-Prohibit. Value sf20 corresponds to 20 subframes, sf40 corresponds to 40 subframes, and so on. See TS 36.321 [6].
longDRX-CycleStartOffset
longDRX-Cycle and drxStartOffset in TS 36.321 [6] unless eDRX-Config-CycleStartOffset is configured. The value of longDRX-Cycle is in number of sub-frames. Value sf10 corresponds to 10 sub-frames, sf20 corresponds to 20 sub-frames and so on. If shortDRX-Cycle is configured, the value of longDRX-Cycle shall be a multiple of the shortDRX-Cycle value. The value of drxStartOffset value is in number of sub-frames. In case longDRX-CycleStartOffset-v1130 is signalled, the UE shall ignore longDRX-CycleStartOffset (i.e. without suffix).
maxHARQ-Tx
Maximum number of transmissions for UL HARQ in TS 36.321 [6].
onDurationTimer
Timer for DRX in TS 36.321 [6]. Value in number of PDCCH sub-frames. Value psf1 corresponds to 1 PDCCH sub-frame, psf2 corresponds to 2 PDCCH sub-frames and so on.
periodicBSR-Timer
Timer for BSR reporting in TS 36.321 [6]. Value in number of sub-frames. Value sf10 corresponds to 10 sub-frames, sf20 corresponds to 20 sub-frames and so on.
periodicPHR-Timer
Timer for PHR reporting in TS 36.321 [6]. Value in number of sub-frames. Value sf10 corresponds to 10 subframes, sf20 corresponds to 20 subframes and so on.
phr-ModeOtherCG
Indicates the mode (i.e. real or virtual) used for the PHR of the activated cells that are part of the other Cell Group (i.e. MCG or SCG), when DC is configured.
prohibitPHR-Timer
Timer for PHR reporting in TS 36.321 [6]. Value in number of sub-frames. Value sf0 corresponds to 0 subframes, sf100 corresponds to 100 subframes and so on.
retxBSR-Timer
Timer for BSR reporting in TS 36.321 [6]. Value in number of sub-frames. Value sf640 corresponds to 640 sub-frames, sf1280 corresponds to 1280 sub-frames and so on.
sCellDeactivationTimer
SCell deactivation timer in TS 36.321 [6]. Value in number of radio frames. Value rf4 corresponds to 4 radio frames, value rf8 corresponds to 8 radio frames and so on. E-UTRAN only configures the field if the UE is configured with one or more SCells other than the PSCell and PUCCH SCell. If the field is absent, the UE shall delete any existing value for this field and assume the value to be set to infinity. The same value applies for each SCell of a Cell Group (i.e. MCG or SCG) (although the associated functionality is performed independently for each SCell). Field sCellDeactivationTimer does not apply for the PUCCH SCell.
shortDRX-Cycle
Short DRX cycle in TS 36.321 [6]. Value in number of sub-frames. Value sf2 corresponds to 2 sub-frames, sf5 corresponds to 5 subframes and so on. In case shortDRX-Cycle-v1130 is signalled, the UE shall ignore shortDRX-Cycle (i.e. without suffix).
sr-ProhibitTimer
Timer for SR transmission on PUCCH in TS 36.321 [6]. Value in number of SR period(s) of shortest SR period of any serving cell with PUCCH. Value 0 means no timer for SR transmission on PUCCH is configured. Value 1 corresponds to one SR period, Value 2 corresponds to 2*SR periods and so on. SR period is defined in TS 36.213 [23, table 10.1.5-1].
stag-Id
Indicates the TAG of an SCell, see TS 36.321 [6]. Uniquely identifies the TAG within the scope of a Cell Group (i.e. MCG or SCG). If the field is not configured for an SCell (e.g. absent in MAC-MainConfigSCell), the SCell is part of the PTAG.
stag-ToAddModList, stag-ToReleaseList
Used to configure one or more STAGs. E-UTRAN ensures that a STAG contains at least one SCell with configured uplink. If, due to SCell release a reconfiguration would result in an 'empty' TAG, E-UTRAN includes release of the concerned TAG.
timeAlignmentTimerSTAG
Indicates the value of the time alignment timer for an STAG, see TS 36.321 [6].
ttiBundling
TRUE indicates that TTI bundling TS 36.321 [6] is enabled while FALSE indicates that TTI bundling is disabled. TTI bundling can be enabled for FDD and for TDD only for configurations 0, 1 and 6. The functionality is performed independently per Cell Group (i.e. MCG or SCG), but E-UTRAN does not configure TTI bundling for the SCG. For a TDD PCell, E-UTRAN does not simultaneously enable TTI bundling and semi-persistent scheduling in this release of specification. Furthermore, for a Cell Group, E-UTRAN does not simultaneously configure TTI bundling and SCells with configured uplink, and E-UTRAN does not simultaneously configure TTI bundling and eIMTA.

-	PDCCH-Config
The IE PDCCH-Config specifies PDCCH monitoring parameters that E-UTRAN may configure for a serving cell.
PDCCH-Config information element
-- ASN1START

PDCCH-ConfigSCell-r13 ::=		SEQUENCE {
	skipMonitoringDCI-format0-1A-r13	ENUMERATED {true}				OPTIONAL,	-- Need OR
	pdcch-candidateReductions-r13		PDCCH-CandidateReductions-r13		OPTIONAL 	-- Need OR
}

PDCCH-CandidateReductionValue-r13 ::= ENUMERATED {n0, n33, n66, n100}

PDCCH-CandidateReductions-r13 ::= SEQUENCE {
	pdcch-candidateReductionAL1		PDCCH-CandidateReductionValue-r13,
	pdcch-candidateReductionAL2		PDCCH-CandidateReductionValue-r13,
	pdcch-candidateReductionAL3		PDCCH-CandidateReductionValue-r13,
	pdcch-candidateReductionAL4		PDCCH-CandidateReductionValue-r13,
	pdcch-candidateReductionAL5		PDCCH-CandidateReductionValue-r13 
}

-- ASN1STOP

PDCCH-Config field descriptions
skipMonitoringDCI-format0-1A 
Indicates the whether UE is configured to omit monitoring DCI fromat 0/1A, see TS 36.213 [23, 9.1].
pdcch-candidateReductionALx
Indicates reduced (E)PDCCH monitoring requirements on user specific search space of the x-th aggregation level, see TS 36.213 [23, 9.1]. n0 corresponds to value 0%, n33 corresponds to 33% and so on.

-	PDCP-Config
The IE PDCP-Config is used to set the configurable PDCP parameters for data radio bearers.
PDCP-Config information element
-- ASN1START

PDCP-Config ::=						SEQUENCE {
	discardTimer						ENUMERATED {
											ms50, ms100, ms150, ms300, ms500,
											ms750, ms1500, infinity
	}															OPTIONAL,			-- Cond Setup
	rlc-AM								SEQUENCE {
		statusReportRequired				BOOLEAN
	}															OPTIONAL,			-- Cond Rlc-AM
	rlc-UM								SEQUENCE {
		pdcp-SN-Size						ENUMERATED {len7bits, len12bits}
	}															OPTIONAL,			-- Cond Rlc-UM
	headerCompression					CHOICE {
		notUsed								NULL,
		rohc								SEQUENCE {
			maxCID								INTEGER (1..16383)				DEFAULT 15,
			profiles							SEQUENCE {
				profile0x0001						BOOLEAN,
				profile0x0002						BOOLEAN,
				profile0x0003						BOOLEAN,
				profile0x0004						BOOLEAN,
				profile0x0006						BOOLEAN,
				profile0x0101						BOOLEAN,
				profile0x0102						BOOLEAN,
				profile0x0103						BOOLEAN,
				profile0x0104						BOOLEAN
			},
			...
		}
	},
	...,
	[[	rn-IntegrityProtection-r10		ENUMERATED {enabled}	OPTIONAL	-- Cond RN
	]],
	[[	pdcp-SN-Size-v1130				ENUMERATED {len15bits}	OPTIONAL	-- Cond Rlc-AM2
	]],
	[[	ul-DataSplitDRB-ViaSCG-r12		BOOLEAN		OPTIONAL,	-- Need ON
		t-Reordering-r12				ENUMERATED {
										ms0, ms20, ms40, ms60, ms80, ms100, ms120, ms140,
										ms160, ms180, ms200, ms220, ms240, ms260, ms280, ms300,
										ms500, ms750, spare14, spare13, spare12, spare11, spare10,
										spare9, spare8, spare7, spare6, spare5, spare4, spare3,
										spare2, spare1}					OPTIONAL	-- Cond SetupS
	]],
	[[	ul-DataSplitThreshold-r13		CHOICE {
			release						NULL,
			setup						ENUMERATED {
										b0, b100, b200, b400, b800, b1600, b3200, b6400, b12800,
										b25600, b51200, b102400, b204800, b409600, b819200,
										spare1}
		}																OPTIONAL,	-- Need ON
		pdcp-SN-Size-v13xx				ENUMERATED {len18bits}	OPTIONAL	-- Cond Rlc-AM3
	]]

}

-- ASN1STOP

PDCP-Config field descriptions
discardTimer
Indicates the discard timer value specified in TS 36.323 [8]. Value in milliseconds. Value ms50 means 50 ms, ms100 means 100 ms and so on.
headerCompression
E-UTRAN does not reconfigure header compression for an MCG DRB except for upon handover and upon the first reconfiguration after RRC connection re-establishment. E-UTRAN does not reconfigure header compression for a SCG DRB except for upon SCG change involving PDCP re-establishment. For split DRBs E-UTRAN configures only notUsed.
maxCID
Indicates the value of the MAX_CID parameter as specified in TS 36.323 [8]. The total value of MAX_CIDs across all bearers for the UE should be less than or equal to the value of maxNumberROHC-ContextSessions parameter as indicated by the UE.
pdcp-SN-Size
Indicates the PDCP Sequence Number length in bits. For RLC UM: value len7bits means that the 7-bit PDCP SN format is used and len12bits means that the 12-bit PDCP SN format is used. For RLC AM: value len15bits means that the 15-bit PDCP SN format is used, value len18bits means that the 18-bit PDCP SN format is used, otherwise if the field is not included upon setup of the PCDP entity 12-bit PDCP SN format is used, as specified in TS 36.323 [8].
profiles
The profiles used by both compressor and decompressor in both UE and E-UTRAN. The field indicates which of the ROHC profiles specified in TS 36.323 [8] are supported, i.e. value true indicates that the profile is supported. Profile 0x0000 shall always be supported when the use of ROHC is configured. If support of two ROHC profile identifiers with the same 8 LSB's is signalled, only the profile corresponding to the highest value shall be applied. E-UTRAN does not configure ROHC while t-Reordering is configured (i.e. for split DRBs or upon reconfiguration from split to MCG DRB).
t-Reordering
Indicates the value of the reordering timer, as specified in TS 36.323 [8]. Value in milliseconds. Value ms0 means 0 ms, ms20 means 20 ms and so on.
rn-IntegrityProtection
Indicates that integrity protection or verification shall be applied for all subsequent packets received and sent by the RN on the DRB.
statusReportRequired
Indicates whether or not the UE shall send a PDCP Status Report upon re-establishment of the PDCP entity and upon PDCP data recovery as specified in TS 36.323 [8].
ul-DataSplitDRB-ViaSCG
Indicates whether the UE shall send PDCP PDUs via SCG as specified in TS 36.323 [8]. E-UTRAN only configures the field (i.e. indicates value TRUE) for split DRBs.
ul-DataSplitThreshold
Indicates the threshold value for uplink data split operation specified in TS 36.323 [8]. Value b100 means 100 Bytes, b200 means 200 Bytes and so on. E-UTRAN only configures this field for split DRBs.

Conditional presence
Explanation
Rlc-AM
The field is mandatory present upon setup of a PDCP entity for a radio bearer configured with RLC AM. The field is optional, need ON, in case of reconfiguration of a PDCP entity at handover, at the first reconfiguration after RRC re-establishment or at SCG change involving PDCP re-establishment or PDCP data recovery for a radio bearer configured with RLC AM. Otherwise the field is not present.
Rlc-AM2
The field is optionally present, need OP, upon setup of a PDCP entity for a radio bearer configured with RLC AM. Otherwise the field is not present.
Rlc-AM3
The field is optionally present, need OP, upon setup of a PDCP entity for a radio bearer configured with RLC AM, if pdcp-SN-Size-v1130 is absent. Otherwise the field is not present.
Rlc-UM
The field is mandatory present upon setup of a PDCP entity for a radio bearer configured with RLC UM. It is optionally present, Need ON, upon handover within E-UTRA, upon the first reconfiguration after re-establishment and upon SCG change involving PDCP re-establishment. Otherwise the field is not present.
RN
The field is optionally present when signalled to the RN, need OR. Otherwise the field is not present.
Setup
The field is mandatory present in case of radio bearer setup. Otherwise the field is optionally present, need ON.
SetupS
The field is mandatory present in case of setup of or reconfiguration to a split DRB. The field is optionally present upon reconfiguration of a split DRB or upon DRB type change from split to MCG DRB, need ON. Otherwise the field is not present.

-	PDSCH-Config
The IE PDSCH-ConfigCommon and the IE PDSCH-ConfigDedicated are used to specify the common and the UE specific PDSCH configuration respectively.
PDSCH-Config information element
-- ASN1START

PDSCH-ConfigCommon ::=		SEQUENCE {
	referenceSignalPower				INTEGER (-60..50),
	p-b									INTEGER (0..3)
}

PDSCH-ConfigDedicated::=		SEQUENCE {
	p-a									ENUMERATED {
											dB-6, dB-4dot77, dB-3, dB-1dot77,
											dB0, dB1, dB2, dB3}
}

PDSCH-ConfigDedicated-v1130 ::=		SEQUENCE {
	dmrs-ConfigPDSCH-r11				DMRS-Config-r11					OPTIONAL,	-- Need ON
	qcl-Operation						ENUMERATED {typeA, typeB}			OPTIONAL,	-- Need OR
	re-MappingQCLConfigToReleaseList-r11	RE-MappingQCLConfigToReleaseList-r11	OPTIONAL,	-- Need ON
	re-MappingQCLConfigToAddModList-r11		RE-MappingQCLConfigToAddModList-r11		OPTIONAL	-- Need ON
}

PDSCH-ConfigDedicated-v1280 ::=		SEQUENCE {
	tbsIndexAlt-r12						ENUMERATED {a26, a33}				OPTIONAL	-- Need OR
}

PDSCH-ConfigDedicated-v13x0 ::=		SEQUENCE {
	dmrs-ConfigPDSCH-v13x0				DMRS-Config-v13x0					OPTIONAL	-- Need ON
}

RE-MappingQCLConfigToAddModList-r11 ::=		SEQUENCE (SIZE (1..maxRE-MapQCL-r11)) OF PDSCH-RE-MappingQCL-Config-r11

RE-MappingQCLConfigToReleaseList-r11 ::=	SEQUENCE (SIZE (1..maxRE-MapQCL-r11)) OF PDSCH-RE-MappingQCL-ConfigId-r11

PDSCH-RE-MappingQCL-Config-r11 ::=		SEQUENCE {
	pdsch-RE-MappingQCL-ConfigId-r11	PDSCH-RE-MappingQCL-ConfigId-r11,
	optionalSetOfFields-r11				SEQUENCE {
		crs-PortsCount-r11					ENUMERATED {n1, n2, n4, spare1},
		crs-FreqShift-r11					INTEGER (0..5),
		mbsfn-SubframeConfigList-r11		CHOICE {
			release								NULL,
			setup								SEQUENCE {
				subframeConfigList					MBSFN-SubframeConfigList
			}
		}																	OPTIONAL,	-- Need ON
		pdsch-Start-r11						ENUMERATED {reserved, n1, n2, n3, n4, assigned}
	}																		OPTIONAL,	-- Need OP
	csi-RS-ConfigZPId-r11				CSI-RS-ConfigZPId-r11,
	qcl-CSI-RS-ConfigNZPId-r11			CSI-RS-ConfigNZPId-r11				OPTIONAL,	-- Need OR
	...
}

-- ASN1STOP

PDSCH-Config field descriptions
optionalSetOfFields
If absent, the UE releases the configuration provided previously, if any, and applies the values from the serving cell configured on the same frequency.
p-a
Parameter: , see TS 36.213 [23, 5.2]. Value dB-6 corresponds to -6 dB, dB-4dot77 corresponds to -4.77 dB etc.
p-b
Parameter: , see TS 36.213 [23, Table 5.2-1].
pdsch-Start
The starting OFDM symbol of PDSCH for the concerned serving cell, see TS 36.213 [23. 7.1.6.4]. Values 1, 2, 3 are applicable when dl-Bandwidth for the concerned serving cell is greater than 10 resource blocks, values 2, 3, 4 are applicable when dl-Bandwidth for the concerned serving cell is less than or equal to 10 resource blocks, see TS 36.211 [21, Table 6.7-1]. Value n1 corresponds to 1, value n2 corresponds to 2 and so on.
qcl-CSI-RS-ConfigNZPId
Indicates the CSI-RS resource that is quasi co-located with the PDSCH antenna ports, see TS 36.213 [23, 7.1.9]. E-UTRAN configures this field if and only if the UE is configured with qcl-Operation set to typeB.
qcl-Operation
Indicates the quasi co-location behaviour to be used by the UE, type A and type B, as described in TS 36.213 [23, 7.1.10].
referenceSignalPower
Parameter: Reference-signal power, which provides the downlink reference-signal EPRE, see TS 36.213 [23, 5.2]. The actual value in dBm.
re-MappingQCLConfigToAddModList, re-MappingQCLConfigToReleaseList
For a serving frequency E-UTRAN configures at least one PDSCH-RE-MappingQCL-Config when transmission mode 10 is configured for the serving cell on this carrier frequency. Otherwise it does not configure this IE.
tbsIndexAlt
Indicates the applicability of the alternative TBS index for the ITBS 26 and 33 (see TS 36.213 [23, Table 7.1.7.2.1-1]) to all subframes scheduled by DCI format 2C or 2D. Value a26 refers to the alternative TBS index ITBS 26A, and value a33 refers to the alternative TBS index ITBS 33A. If this field is not configured, the UE shall use ITBS 26 and 33 specified in Table 7.1.7.2.1-1 in TS 36.213 [23] for all subframes instead.

-	PDSCH-RE-MappingQCL-ConfigId
The IE PDSCH-RE-MappingQCL-ConfigId is used to identify a set of PDSCH parameters related to resource element mapping and quasi co-location, as configured by the IE PDSCH-RE-MappingQCL-Config. The identity is unique within the scope of a carrier frequency.
PDSCH-RE-MappingQCL-ConfigId information elements
-- ASN1START

PDSCH-RE-MappingQCL-ConfigId-r11 ::=		INTEGER (1..maxRE-MapQCL-r11)

-- ASN1STOP

-	PHICH-Config
The IE PHICH-Config is used to specify the PHICH configuration.
PHICH-Config information element
-- ASN1START

PHICH-Config ::=					SEQUENCE {
	phich-Duration						ENUMERATED {normal, extended},
	phich-Resource						ENUMERATED {oneSixth, half, one, two}
}

-- ASN1STOP

PHICH-Config field descriptions
phich-Duration
Parameter: PHICH-Duration, see TS 36.211 [21, Table 6.9.3-1].
phich-Resource
Parameter: Ng, see TS 36.211 [21, 6.9]. Value oneSixth corresponds to 1/6, half corresponds to 1/2 and so on.

-	PhysicalConfigDedicated
The IE PhysicalConfigDedicated is used to specify the UE specific physical channel configuration.
PhysicalConfigDedicated information element
-- ASN1START

PhysicalConfigDedicated ::=		SEQUENCE {
	pdsch-ConfigDedicated				PDSCH-ConfigDedicated			OPTIONAL,		-- Need ON
	pucch-ConfigDedicated				PUCCH-ConfigDedicated			OPTIONAL,		-- Need ON
	pusch-ConfigDedicated				PUSCH-ConfigDedicated			OPTIONAL,		-- Need ON
	uplinkPowerControlDedicated			UplinkPowerControlDedicated		OPTIONAL,		-- Need ON
	tpc-PDCCH-ConfigPUCCH				TPC-PDCCH-Config 				OPTIONAL,		-- Need ON
	tpc-PDCCH-ConfigPUSCH				TPC-PDCCH-Config 				OPTIONAL,		-- Need ON
	cqi-ReportConfig					CQI-ReportConfig				OPTIONAL,		-- Cond CQI-r8
	soundingRS-UL-ConfigDedicated		SoundingRS-UL-ConfigDedicated	OPTIONAL,		-- Need ON
	antennaInfo							CHOICE {
		explicitValue						AntennaInfoDedicated,
		defaultValue						NULL
	}		OPTIONAL,																-- Cond AI-r8
	schedulingRequestConfig				SchedulingRequestConfig		OPTIONAL, 			-- Need ON
	...,
	[[	cqi-ReportConfig-v920				CQI-ReportConfig-v920		OPTIONAL,		-- Cond CQI-r8
		antennaInfo-v920					AntennaInfoDedicated-v920	OPTIONAL		-- Cond AI-r8
	]],
	[[	antennaInfo-r10					CHOICE {
			explicitValue-r10				AntennaInfoDedicated-r10,
			defaultValue					NULL
		}		OPTIONAL,															-- Cond AI-r10
		antennaInfoUL-r10				AntennaInfoUL-r10				OPTIONAL,		-- Need ON
		cif-Presence-r10				BOOLEAN							OPTIONAL,	-- Need ON
		cqi-ReportConfig-r10			CQI-ReportConfig-r10			OPTIONAL,		-- Cond CQI-r10
		csi-RS-Config-r10				CSI-RS-Config-r10				OPTIONAL,		-- Need ON
		pucch-ConfigDedicated-v1020		PUCCH-ConfigDedicated-v1020		OPTIONAL,		-- Need ON
		pusch-ConfigDedicated-v1020		PUSCH-ConfigDedicated-v1020		OPTIONAL,		-- Need ON
		schedulingRequestConfig-v1020	SchedulingRequestConfig-v1020	OPTIONAL,		-- Need ON
		soundingRS-UL-ConfigDedicated-v1020
								SoundingRS-UL-ConfigDedicated-v1020		OPTIONAL,		-- Need ON
		soundingRS-UL-ConfigDedicatedAperiodic-r10
								SoundingRS-UL-ConfigDedicatedAperiodic-r10	OPTIONAL,	-- Need ON
		uplinkPowerControlDedicated-v1020	UplinkPowerControlDedicated-v1020	OPTIONAL	-- Need ON
	]],
	[[	additionalSpectrumEmissionCA-r10 			CHOICE {
			release									NULL,
			setup									SEQUENCE {
				additionalSpectrumEmissionPCell-r10		AdditionalSpectrumEmission
			}
		}			OPTIONAL	-- Need ON
	]],
	[[	-- DL configuration as well as configuration applicable for DL and UL
		csi-RS-ConfigNZPToReleaseList-r11	CSI-RS-ConfigNZPToReleaseList-r11	OPTIONAL,	-- Need ON
		csi-RS-ConfigNZPToAddModList-r11	CSI-RS-ConfigNZPToAddModList-r11	OPTIONAL,	-- Need ON
		csi-RS-ConfigZPToReleaseList-r11	CSI-RS-ConfigZPToReleaseList-r11	OPTIONAL,	-- Need ON
		csi-RS-ConfigZPToAddModList-r11		CSI-RS-ConfigZPToAddModList-r11	OPTIONAL,	-- Need ON
		epdcch-Config-r11					EPDCCH-Config-r11				OPTIONAL,	-- Need ON
		pdsch-ConfigDedicated-v1130			PDSCH-ConfigDedicated-v1130		OPTIONAL,	-- Need ON
	-- UL configuration
		cqi-ReportConfig-v1130				CQI-ReportConfig-v1130			OPTIONAL,	-- Need ON
		pucch-ConfigDedicated-v1130			PUCCH-ConfigDedicated-v1130		OPTIONAL,	-- Need ON
		pusch-ConfigDedicated-v1130			PUSCH-ConfigDedicated-v1130		OPTIONAL,	-- Need ON
		uplinkPowerControlDedicated-v1130	UplinkPowerControlDedicated-v1130	OPTIONAL	-- Need ON
	]],
	[[	antennaInfo-v1250					AntennaInfoDedicated-v1250		OPTIONAL,	-- Cond AI-r10
		eimta-MainConfig-r12				EIMTA-MainConfig-r12			OPTIONAL,	-- Need ON
		eimta-MainConfigPCell-r12			EIMTA-MainConfigServCell-r12		OPTIONAL,	-- Need ON
		pucch-ConfigDedicated-v1250			PUCCH-ConfigDedicated-v1250		OPTIONAL,	-- Need ON
		cqi-ReportConfigPCell-v1250			CQI-ReportConfig-v1250			OPTIONAL,	-- Need ON
		uplinkPowerControlDedicated-v1250	UplinkPowerControlDedicated-v1250	OPTIONAL,	-- Need ON
		pusch-ConfigDedicated-v1250		PUSCH-ConfigDedicated-v1250		OPTIONAL,	-- Need ON
		csi-RS-Config-v1250					CSI-RS-Config-v1250				OPTIONAL	-- Need ON
	]],
	[[	pdsch-ConfigDedicated-v1280			PDSCH-ConfigDedicated-v1280		OPTIONAL	-- Need ON
	]],
	[[	pdsch-ConfigDedicated-v13x0			PDSCH-ConfigDedicated-v13x0		OPTIONAL,	-- Need ON
		pucch-ConfigDedicated-r13			PUCCH-ConfigDedicated-v13xy		OPTIONAL,	-- Need ON
		pusch-ConfigDedicated-r13			PUSCH-ConfigDedicated-v13xy		OPTIONAL,	-- Need ON
		cqi-ReportConfig-v13xy					CQI-ReportConfig-v13xy		OPTIONAL,	-- Need ON
		soundingRS-UL-ConfigDedicated-v13x0
								SoundingRS-UL-ConfigDedicated-v13x0		OPTIONAL,		-- Need ON
		soundingRS-UL-ConfigDedicatedUpPTsExt-r13
								SoundingRS-UL-ConfigDedicatedUpPTsExt-r13		OPTIONAL,		-- Need ON
		soundingRS-UL-ConfigDedicatedAperiodic-v13x0
								SoundingRS-UL-ConfigDedicatedAperiodic-v13x0	OPTIONAL,	-- Need ON
		soundingRS-UL-ConfigDedicatedAperiodicUpPTsExt-r13
								SoundingRS-UL-ConfigDedicatedAperiodicUpPTsExt-r13		OPTIONAL,		-- Need ON
		cqi-ReportConfigPCell-v13x0			CQI-ReportConfig-v13xy			OPTIONAL,	-- Need ON
		csi-RS-Config-v13x0					CSI-RS-Config-v13x0				OPTIONAL	-- Need ON
	]]
}

PhysicalConfigDedicatedSCell-r10 ::=		SEQUENCE {
	-- DL configuration as well as configuration applicable for DL and UL
	nonUL-Configuration-r10					SEQUENCE {
		antennaInfo-r10							AntennaInfoDedicated-r10	OPTIONAL,	-- Need ON
		crossCarrierSchedulingConfig-r10		CrossCarrierSchedulingConfig-r10	OPTIONAL,	-- Need ON
		csi-RS-Config-r10						CSI-RS-Config-r10			OPTIONAL,	-- Need ON
		pdsch-ConfigDedicated-r10				PDSCH-ConfigDedicated		OPTIONAL	-- Need ON
	}																OPTIONAL, 	-- Cond SCellAdd
	-- UL configuration
	ul-Configuration-r10					SEQUENCE {
		antennaInfoUL-r10						AntennaInfoUL-r10			OPTIONAL,	-- Need ON
		pusch-ConfigDedicatedSCell-r10			PUSCH-ConfigDedicatedSCell-r10		OPTIONAL,	-- Need ON
		uplinkPowerControlDedicatedSCell-r10	UplinkPowerControlDedicatedSCell-r10	OPTIONAL,	-- Need ON
		cqi-ReportConfigSCell-r10				CQI-ReportConfigSCell-r10	OPTIONAL,	-- Need ON
		soundingRS-UL-ConfigDedicated-r10		SoundingRS-UL-ConfigDedicated	OPTIONAL,	-- Need ON
		soundingRS-UL-ConfigDedicated-v1020
								SoundingRS-UL-ConfigDedicated-v1020	OPTIONAL,		-- Need ON
		soundingRS-UL-ConfigDedicatedAperiodic-r10
								SoundingRS-UL-ConfigDedicatedAperiodic-r10	OPTIONAL	-- Need ON
	}																	OPTIONAL,	-- Cond CommonUL
	...,
	[[	-- DL configuration as well as configuration applicable for DL and UL
		csi-RS-ConfigNZPToReleaseList-r11	CSI-RS-ConfigNZPToReleaseList-r11	OPTIONAL,	-- Need ON
		csi-RS-ConfigNZPToAddModList-r11	CSI-RS-ConfigNZPToAddModList-r11	OPTIONAL,	-- Need ON
		csi-RS-ConfigZPToReleaseList-r11	CSI-RS-ConfigZPToReleaseList-r11	OPTIONAL,	-- Need ON
		csi-RS-ConfigZPToAddModList-r11		CSI-RS-ConfigZPToAddModList-r11	OPTIONAL,	-- Need ON
		epdcch-Config-r11					EPDCCH-Config-r11				OPTIONAL,	-- Need ON
		pdsch-ConfigDedicated-v1130			PDSCH-ConfigDedicated-v1130		OPTIONAL,	-- Need ON
	-- UL configuration
		cqi-ReportConfig-v1130				CQI-ReportConfig-v1130			OPTIONAL,	-- Need ON
		pusch-ConfigDedicated-v1130				PUSCH-ConfigDedicated-v1130	OPTIONAL,	-- Need ON
		uplinkPowerControlDedicatedSCell-v1130	UplinkPowerControlDedicated-v1130	OPTIONAL	-- Need ON
	]],
	[[	antennaInfo-v1250					AntennaInfoDedicated-v1250		OPTIONAL,	-- Need ON
		eimta-MainConfigSCell-r12			EIMTA-MainConfigServCell-r12	OPTIONAL,	-- Need ON
		cqi-ReportConfigSCell-v1250			CQI-ReportConfig-v1250			OPTIONAL,	-- Need ON 
		uplinkPowerControlDedicatedSCell-v1250	UplinkPowerControlDedicated-v1250	OPTIONAL,	-- Need ON
		csi-RS-Config-v1250					CSI-RS-Config-v1250				OPTIONAL	-- Need ON
	]],
	[[	pdsch-ConfigDedicated-v1280			PDSCH-ConfigDedicated-v1280		OPTIONAL	-- Need ON
	]],
	[[	pucch-ConfigDedicated-r13			PUCCH-ConfigDedicated		OPTIONAL,	-- Need ON
		pucch-ConfigDedicatedExt1-r13		PUCCH-ConfigDedicated-v1020	OPTIONAL,	-- Need ON
		pucch-ConfigDedicatedExt2-r13		PUCCH-ConfigDedicated-v1130	OPTIONAL,	-- Need ON
		pucch-ConfigDedicatedExt3-r13		PUCCH-ConfigDedicated-v1250	OPTIONAL,	-- Cond eimta
		pucch-ConfigDedicatedExt4-r13		PUCCH-ConfigDedicated-v13xy	OPTIONAL,	-- Need ON
		pucch-Cell-r13						ENUMERATED {true}			OPTIONAL,	-- Cond PUCCH_SCell
		crossCarrierSchedulingConfig-r13	CrossCarrierSchedulingConfig-r13	 OPTIONAL,	-- Cond Cross-Carrier-Config
		schedulingRequestConfig-r13			SchedulingRequestConfig		OPTIONAL,		-- Need ON
		schedulingRequestConfigExt-r13		SchedulingRequestConfig-v1020	OPTIONAL,	-- Need ON
		tpc-PDCCH-ConfigPUCCH-SCell-r13		TPC-PDCCH-ConfigSCell		OPTIONAL,	-- Cond PUCCH-SCell
		pusch-ConfigDedicated-r13			PUSCH-ConfigDedicated		OPTIONAL,	-- Cond PUSCH-SCell
		pusch-ConfigDedicatedExt-r13		PUSCH-ConfigDedicated-v1020	OPTIONAL,	-- Cond PUSCH-SCell
		pusch-ConfigDedicatedExt2-r13		PUSCH-ConfigDedicated-v13xy	OPTIONAL,	-- Cond PUSCH-SCell
		uplinkPowerControlDedicated-r13		UplinkPowerControlDedicated	OPTIONAL,	-- Cond UL-Power-SCell
		uplinkPowerControlDedicatedExt-r13	UplinkPowerControlDedicated-v1020	OPTIONAL,	-- Cond UL-Power-SCell
		pdcch-ConfigSCell-r13				PDCCH-ConfigSCell-r13		OPTIONAL,	-- Need ON
		cqi-ReportConfig-v13xy					CQI-ReportConfig-v13xy				OPTIONAL,	-- Need ON
		pdsch-ConfigDedicated-v13x0			PDSCH-ConfigDedicated-v13x0		OPTIONAL,	-- Need ON
		soundingRS-UL-ConfigDedicated-v13x0
								SoundingRS-UL-ConfigDedicated-v13x0		OPTIONAL,		-- Need ON
		soundingRS-UL-ConfigDedicatedUpPTsExt-r13
								SoundingRS-UL-ConfigDedicatedUpPTsExt-r13		OPTIONAL,		-- Need ON
		soundingRS-UL-ConfigDedicatedAperiodic-v13x0
								SoundingRS-UL-ConfigDedicatedAperiodic-v13x0	OPTIONAL,	-- Need ON
		soundingRS-UL-ConfigDedicatedAperiodicUpPTsExt-r13
								SoundingRS-UL-ConfigDedicatedAperiodicUpPTsExt-r13		OPTIONAL,		-- Need ON
		csi-RS-Config-v13x0					CSI-RS-Config-v13x0				OPTIONAL,	-- Need ON
		laa-SCellConfiguration-r13		LAA-SCellConfiguration-r13		OPTIONAL	-- Need ON
	]]
}

LAA-SCellConfiguration-r13 ::=			SEQUENCE {
	subframeStartPosition				ENUMERATED {s0, s07},
	laa-SCellSubframeConfig				BIT STRING (SIZE(8))
}

CSI-RS-ConfigNZPToAddModList-r11 ::=	SEQUENCE (SIZE (1..maxCSI-RS-NZP-r11)) OF CSI-RS-ConfigNZP-r11

CSI-RS-ConfigNZPToReleaseList-r11 ::=	SEQUENCE (SIZE (1..maxCSI-RS-NZP-r11)) OF CSI-RS-ConfigNZPId-r11

CSI-RS-ConfigZPToAddModList-r11 ::=	SEQUENCE (SIZE (1..maxCSI-RS-ZP-r11)) OF CSI-RS-ConfigZP-r11

CSI-RS-ConfigZPToReleaseList-r11 ::=	SEQUENCE (SIZE (1..maxCSI-RS-ZP-r11)) OF CSI-RS-ConfigZPId-r11

-- ASN1STOP

PhysicalConfigDedicated field descriptions
additionalSpectrumEmissionPCell
E-UTRAN does not configure this field in this release of the specification.
antennaInfo
A choice is used to indicate whether the antennaInfo is signalled explicitly or set to the default antenna configuration as specified in section 9.2.4.
csi-RS-Config
For a serving frequency E-UTRAN does not configure csi-RS-Config (includes zeroTxPowerCSI-RS) when transmission mode 10 is configured for the serving cell on this carrier frequency.
csi-RS-ConfigNZPToAddModList
For a serving frequency E-UTRAN configures one or more CSI-RS-ConfigNZP only when transmission mode 10 is configured for the serving cell on this carrier frequency. EUTRAN configures a maximum of one CSI-RS-ConfigNZP for a serving frequency on which the UE supports only one CSI process (i.e. supportedCSI-Proc is indicated as n1).
csi-RS-ConfigZPToAddModList
For a serving frequency E-UTRAN configures one or more CSI-RS-ConfigZP only when transmission mode 10 is configured for the serving cell on this carrier frequency.
eimta-MainConfigPCell, eimta-MainConfigSCell
If E-UTRAN configures eimta-MainConfigPCell or eimta-MainConfigSCell for one serving cell in a frequency band, E-UTRAN configures eimta-MainConfigPCell or eimta-MainConfigSCell for all serving cells residing on the frequency band. E-UTRAN configures eimta-MainConfigPCell or eimta-MainConfigSCell only if eimta-MainConfig is configured.
epdcch-Config
indicates the EPDCCH-Config for the cell. E-UTRAN does not configure EPDCCH-Config for an SCell that is configured with value other for schedulingCellInfo in CrossCarrierSchedulingConfig.
laa-SCellSubframeConfig
A bit-map indicating LAA SCell subframe configuration, "1" denotes that the corresponding subframe is allocated as MBSFN subframe. The bitmap is interpreted as follows:
Starting from the first/leftmost bit in the bitmap, the allocation applies to subframes #1, #2, #3 , #4, #6, #7, #8,and #9.
pdsch-ConfigDedicated-v1130
For a serving frequency E-UTRAN configures pdsch-ConfigDedicated-v1130 only when transmission mode 10 is configured for the serving cell on this carrier frequency.
pdsch-ConfigDedicated-v1280
For a serving frequency E-UTRAN configures pdsch-ConfigDedicated-v1280 only when transmission mode 9 or 10 is configured for the serving cell on this carrier frequency.
pucch-Cell
If PUCCH feedback of this SCell is not sent on PCell or PSCell, this field is  present if SCell is used to send PUCCH feedback of this SCell (or cell).
pusch-ConfigDedicated-v1250
E-UTRAN configures pusch-ConfigDedicated-v1250 only if tpc-SubframeSet is configured.
subframeStartPosition
Indicates possible starting positions of transmission in the first subframe of the DL transmission burst, see TS 36.211 [21].Value s0 means the starting position is subframe boundary, s07 means the starting position is either subfarme boundary or slot boundary.
tpc-PDCCH-ConfigPUCCH
PDCCH configuration for power control of PUCCH using format 3/3A, see TS 36.212 [22].
tpc-PDCCH-ConfigPUSCH
PDCCH configuration for power control of PUSCH using format 3/3A, see TS 36.212 [22].
uplinkPowerControlDedicated
E-UTRAN configures uplinkPowerControlDedicated-v1130 only if uplinkPowerControlDedicated (without suffix) is configured.
uplinkPowerControlDedicatedSCell
E-UTRAN configures uplinkPowerControlDedicatedSCell-v1130 only if uplinkPowerControlDedicatedSCell-r10 is configured for this serving cell.

Conditional presence
Explanation
AI-r8
The field is optionally present, need ON, if antennaInfoDedicated-r10 is absent. Otherwise the field is not present
AI-r10
The field is optionally present, need ON, if antennaInfoDedicated is absent. Otherwise the field is not present
CommonUL
The field is mandatory present if ul-Configuration of RadioResourceConfigCommonSCell-r10 is present; otherwise it is optional, need ON.
CQI-r8
The field is optionally present, need ON, if cqi-ReportConfig-r10 is absent. Otherwise the field is not present
CQI-r10
The field is optionally present, need ON, if cqi-ReportConfig is absent. Otherwise the field is not present
Cross-Carrier-Config
The field is optionally present, need ON, if crossCarrierSchedulingConfig-r10 is absent. Otherwise the field is not present
PUCCH-SCell
The field is optionally present for PUCCH SCell. Otherwise it is not present.
PUSCH-SCell
The field is optionally present, need ON, if PUSCH-ConfigDedicatedSCell is absent. Otherwise the field is not present
SCellAdd
The field is mandatory present if cellIdentification is present; otherwise it is optional, need ON.
UL-Power-SCell
The field is optionally present, need ON, if uplinkPowerControlDedicatedSCell is absent. Otherwise the field is not present

NOTE 1:	During handover, the UE performs a MAC reset, which involves reverting to the default CQI/ SRS/ SR configuration in accordance with subclause 5.3.13 and TS 36.321 [6, 5.9 & 5.2]. Hence, for these parts of the dedicated radio resource configuration, the default configuration (rather than the configuration used in the source PCell) is used as the basis for the delta signalling that is included in the message used to perform handover.
NOTE 2:	Since delta signalling is not supported for the common SCell configuration, E-UTRAN can only add or release the uplink of an SCell by releasing and adding the concerned SCell.
-	P-Max
The IE P-Max is used to limit the UE's uplink transmission power on a carrier frequency and is used to calculate the parameter Pcompensation defined in TS 36.304 [4]. Corresponds to parameter PEMAX or PEMAX,c in TS 36.101 [42]. The UE transmit power on one serving cell shall not exceed the configured maximum UE output power of the serving cell determined by this value as specified in TS 36.101 [42, 6.2.5 or 6.2.5A] or, when transmitting sidelink discovery announcements within the coverage of the concerned cell, as specified in TS 36.101 [42, 6.2.5D].
P-Max information element
-- ASN1START

P-Max ::=				INTEGER (-30..33)

-- ASN1STOP

-	PRACH-Config
The IE PRACH-ConfigSIB and IE PRACH-Config are used to specify the PRACH configuration in the system information and in the mobility control information, respectively.
PRACH-Config information elements
-- ASN1START

PRACH-ConfigSIB ::=				SEQUENCE {
	rootSequenceIndex					INTEGER (0..837),
	prach-ConfigInfo					PRACH-ConfigInfo
}

PRACH-Config ::=					SEQUENCE {
	rootSequenceIndex					INTEGER (0..837),
	prach-ConfigInfo					PRACH-ConfigInfo					OPTIONAL	-- Need ON
}

PRACH-ConfigSCell-r10 ::=				SEQUENCE {
	prach-ConfigIndex-r10					INTEGER (0..63)
}

PRACH-ConfigInfo ::=				SEQUENCE {
	prach-ConfigIndex					INTEGER (0..63),
	highSpeedFlag						BOOLEAN,
	zeroCorrelationZoneConfig			INTEGER (0..15),
	prach-FreqOffset					INTEGER (0..94)
}

-- ASN1STOP

PRACH-Config field descriptions
highSpeedFlag
Parameter: High-speed-flag, see TS 36.211, [21, 5.7.2].TRUE corresponds to Restricted set and FALSE to Unrestricted set.
prach-ConfigIndex
Parameter: prach-ConfigurationIndex, see TS 36.211 [21, 5.7.1].
prach-FreqOffset
Parameter: prach-FrequencyOffset, see TS 36.211, [21, 5.7.1]. For TDD the value range is dependent on the value of prach-ConfigIndex.
rootSequenceIndex
Parameter: RACH_ROOT_SEQUENCE, see TS 36.211 [21, 5.7.1].
zeroCorrelationZoneConfig
Parameter: NCS configuration, see TS 36.211, [21, 5.7.2: table 5.7.2-2] for preamble format 0..3 and TS 36.211, [21, 5.7.2: table 5.7.2-3] for preamble format 4.

-	PresenceAntennaPort1
The IE PresenceAntennaPort1 is used to indicate whether all the neighbouring cells use Antenna Port 1. When set to TRUE, the UE may assume that at least two cell-specific antenna ports are used in all neighbouring cells.
PresenceAntennaPort1 information element
-- ASN1START

PresenceAntennaPort1 ::=				BOOLEAN

-- ASN1STOP

-	PUCCH-Config
The IE PUCCH-ConfigCommon and IE PUCCH-ConfigDedicated are used to specify the common and the UE specific PUCCH configuration respectively.
PUCCH-Config information elements
-- ASN1START

PUCCH-ConfigCommon ::=				SEQUENCE {
	deltaPUCCH-Shift					ENUMERATED {ds1, ds2, ds3},
	nRB-CQI								INTEGER (0..98),
	nCS-AN								INTEGER (0..7),
	n1PUCCH-AN							INTEGER (0..2047)
}

PUCCH-ConfigDedicated ::=			SEQUENCE {
	ackNackRepetition					CHOICE{
		release								NULL,
		setup								SEQUENCE {
			repetitionFactor					ENUMERATED {n2, n4, n6, spare1},
			n1PUCCH-AN-Rep						INTEGER (0..2047)
		}
	},
	tdd-AckNackFeedbackMode				ENUMERATED {bundling, multiplexing}	OPTIONAL	-- Cond TDD
}

PUCCH-ConfigDedicated-v1020 ::=		SEQUENCE {
	pucch-Format-r10					CHOICE {
		format3-r10								SEQUENCE {
			n3PUCCH-AN-List-r10	SEQUENCE (SIZE (1..4)) OF INTEGER (0..549)	OPTIONAL,	-- Need ON
			twoAntennaPortActivatedPUCCH-Format3-r10		CHOICE {	
				release											NULL,
				setup											SEQUENCE {
					n3PUCCH-AN-ListP1-r10	SEQUENCE (SIZE (1..4)) OF INTEGER (0..549)
				}
			}																OPTIONAL	-- Need ON
		},
		channelSelection-r10				SEQUENCE {
			n1PUCCH-AN-CS-r10					CHOICE {
				release								NULL,
				setup								SEQUENCE {
					n1PUCCH-AN-CS-List-r10				SEQUENCE (SIZE (1..2)) OF N1PUCCH-AN-CS-r10
				}
			}																OPTIONAL	-- Need ON
		}
	}																		OPTIONAL,	-- Need OR
	twoAntennaPortActivatedPUCCH-Format1a1b-r10		ENUMERATED {true}		OPTIONAL,	-- Need OR
	simultaneousPUCCH-PUSCH-r10						ENUMERATED {true}		OPTIONAL,	-- Need OR
	n1PUCCH-AN-RepP1-r10							INTEGER (0..2047)		OPTIONAL	-- Need OR
}

PUCCH-ConfigDedicated-v1130 ::=		SEQUENCE {
	n1PUCCH-AN-CS-v1130					CHOICE {
		release								NULL,
		setup								SEQUENCE {
			n1PUCCH-AN-CS-ListP1-r11			SEQUENCE (SIZE (2..4)) OF INTEGER (0..2047)
		}
	}																		OPTIONAL,	-- Need ON
	nPUCCH-Param-r11					CHOICE {
		release								NULL,
		setup								SEQUENCE {
			nPUCCH-Identity-r11					INTEGER (0..503),
			n1PUCCH-AN-r11						INTEGER (0..2047)
		}
	}																		OPTIONAL	-- Need ON
}

PUCCH-ConfigDedicated-v1250 ::=		SEQUENCE {
	nkaPUCCH-Param-r12					CHOICE {
		release								NULL,
		setup								SEQUENCE {
			nkaPUCCH-AN-r12						INTEGER (0..2047)
		}
	}
}

PUCCH-ConfigDedicated-v13xy ::=		SEQUENCE {
	spatialBundlingPUCCH				BOOLEAN,
	spatialBundlingPUSCH				BOOLEAN,
	harq-TimingTDD						BOOLEAN,
	codebooksizeDetermination-r13		INTEGER(0..1),
	maximumPayloadCoderate-r13			INTEGER (0..7), 	 
	pucch-Format-r13					CHOICE {
		format4-r13							SEQUENCE {
			format4-resourceConfiguration			SEQUENCE (SIZE (4)) OF Format4-resource-r13,
			format4-MultiCSI-resourceConfiguration	SEQUENCE (SIZE (1..2)) OF Format4-resource-r13 OPTIONAL 	-- Need OR
		},
		format5-r13				SEQUENCE {
			format5-resourceConfiguration			SEQUENCE (SIZE (4)) OF Format5-resource-r13,
			format5-MultiCSI-resourceConfiguration	SEQUENCE (SIZE (1..2)) OF Format5-resource-r13 OPTIONAL 	-- Need OR

		}
	}															OPTIONAL	-- Need OR
}

Format4-resource-r13	::=				SEQUENCE {
	startingPRB-format4-r13	  					INTEGER (0..109),
	numberOfPRB-format4-r13  					INTEGER (0..7)
}
 
Format5-resource-r13	::=				SEQUENCE {
	startingPRB-format5-r13	  					INTEGER (0..109),
	cdm-index-format5-r13  						INTEGER (0..1)
}



N1PUCCH-AN-CS-r10	::= SEQUENCE (SIZE (1..4)) OF INTEGER (0..2047)

-- ASN1STOP

PUCCH-Config field descriptions
ackNackRepetition
Parameter indicates whether ACK/NACK repetition is configured, see TS 36.213 [23, 10.1].
codebooksizeDetermination
Parameter indicates whether HARQ codebook size is determined with downlink assignment indicator based solution or number of configured CCs, see TS 36.213 [23, 7.3].
deltaPUCCH-Shift
Parameter: , see 36.211 [21, 5.4.1], where ds1 corresponds to value 1 ds2 to 2 etc.
harq-TimingTDD
Parameter indicates for a TDD SCell when aggregated with a TDD PCell of different UL/DL configurations whether deriving the HARQ timing for such a cell is done in the same way as the DL HARQ timing of an FDD SCell with a TDD PCell, see TS 36.213 [23, 10.2].
maximumPayloadCoderate
Parameter xx see TS 36.213 [23,7.2]. Maximum payload or code rate for multi P-CSI on each PUCCH resource.
n1PUCCH-AN
Parameter: , see TS 36.213 [23, 10.1].
n1PUCCH-AN-r11 indicates UE-specific PUCCH AN resource offset, see TS 36.213 [23, 10.1].
n1PUCCH-AN-CS-List
Parameter:  for antenna port  for PUCCH format 1b with channel selection, see TS 36.213 [23, 10.1.2.2.1, 10.1.3.2.1].
n1PUCCH-AN-CS-ListP1
Parameter: for antenna port  for PUCCH format 1b with channel selection, see TS 36.213 [23, 10.1]. E-UTRAN configures this field only when pucch-Format is set to channelSelection.
n1PUCCH-AN-Rep, n1PUCCH-AN-RepP1
Parameter: for antenna port P0 and for antenna port P1 respectively, see TS 36.213 [23, 10.1].
n3PUCCH-AN-List, n3PUCCH-AN-ListP1
Parameter: for antenna port P0 and for antenna port P1 respectively, see TS 36.213 [23, 10.1]. 
nCS-An
Parameter: see TS 36.211 [21, 5.4].
nkaPUCCH-AN
Parameter: , see TS 36.213 [23, 10.1.3].
nkaPUCCH-AN-r12 indicates PUCCH format 1a/1b starting offset for the subframe set , see TS 36.213 [23, 10.1.3]. E-UTRAN configures nkaPUCCH-AN only if eimta-MainConfig is configured.
nPUCCH-Identity
Parameter: , see TS 36.211 [21, 5.5.1.5].
nRB-CQI
Parameter: , see TS 36.211 [21, 5.4].
numberOfPRB-format4, startingPRB-format4
Parameter see TS 36.213 [23,x.y]. PUCCH resource(s) of PUCCH format 4.
numberOfPRB-format5, cdm-index-format5
Parameter see TS 36.213 [23,x.y]. PUCCH resource(s) of PUCCH format 5.
pucch-Format
Parameter indicates one of the PUCCH formats for transmission of HARQ-ACK, see TS 36.213 [23, 10.1]. For TDD, if the UE is configured with PCell only, the channelSelection indicates the transmission of HARQ-ACK multiplexing as defined in Tables 10.1.3-5, 10.1.3-6, and 10.1.3-7 in TS 36.213 [23] for PUCCH, and in 7.3 in TS 36.213 [23] for PUSCH.
repetitionFactor
Parameter  see TS 36.213 [23, 10.1] where n2 corresponds to repetition factor 2, n4 to 4.
simultaneousPUCCH-PUSCH
Parameter indicates whether simultaneous PUCCH and PUSCH transmissions is configured, see TS 36.213 [23, 10.1 and 5.1.1]. E-UTRAN configures this field for the PCell, only when the nonContiguousUL-RA-WithinCC-Info is set to supported in the band on which PCell is configured. Likewise, E-UTRAN configures this field for the PSCell, only when the nonContiguousUL-RA-WithinCC-Info is set to supported in the band on which PSCell is configured. Likewise, E-UTRAN configures this field for the PUCCH SCell, only when the nonContiguousUL-RA-WithinCC-Info is set to supported in the band on which PUCCH SCell is configured.
spatialBundlingPUCCH
Parameter indicates whether spatial bundling is enabled or not for PUCCH, see TS 36.213 [23, 7.3]
spatialBundlingPUSCH
Parameter indicates whether spatial bundling is enabled or not for PUSCH, see TS 36.213 [23, 7.3]
tdd-AckNackFeedbackMode
Parameter indicates one of the TDD ACK/NACK feedback modes used, see TS 36.213 [23, 7.3 and 10.1.3]. The value bundling corresponds to use of ACK/NACK bundling whereas, the value multiplexing corresponds to ACK/NACK multiplexing as defined in Tables 10.1.3-2, 10.1.3-3, and 10.1.3-4 in TS 36.213 [23]. The same value applies to both ACK/NACK feedback modes on PUCCH as well as on PUSCH.
twoAntennaPortActivatedPUCCH-Format1a1b
Indicates whether two antenna ports are configured for PUCCH format 1a/1b for HARQ-ACK, see TS 36.213 [23, 10.1]. The field also applies for PUCCH format 1a/1b transmission when format3 is configured, see TS 36.213 [23, 10.1.2.2.2, 10.1.3.2.2].
twoAntennaPortActivatedPUCCH-Format3
Indicates whether two antenna ports are configured for PUCCH format 3 for HARQ-ACK, see TS 36.213 [23, 10.1].

Conditional presence
Explanation
TDD
The field is mandatory present for TDD if the pucch-Format is not present. If the pucch-Format is present, the field is not present and the UE shall delete any existing value for this field. It is not present for FDD and the UE shall delete any existing value for this field.

-	PUSCH-Config
The IE PUSCH-ConfigCommon is used to specify the common PUSCH configuration and the reference signal configuration for PUSCH and PUCCH. The IE PUSCH-ConfigDedicated is used to specify the UE specific PUSCH configuration.
PUSCH-Config information element
-- ASN1START

PUSCH-ConfigCommon ::=				SEQUENCE {
	pusch-ConfigBasic					SEQUENCE {
		n-SB								INTEGER (1..4),
		hoppingMode							ENUMERATED {interSubFrame, intraAndInterSubFrame},
		pusch-HoppingOffset					INTEGER (0..98),
		enable64QAM							BOOLEAN
	},
	ul-ReferenceSignalsPUSCH			UL-ReferenceSignalsPUSCH
}

PUSCH-ConfigCommon-v1270 ::=		SEQUENCE {
	enable64QAM-v1270						ENUMERATED {true}
}

PUSCH-ConfigDedicated ::=			SEQUENCE {
	betaOffset-ACK-Index				INTEGER (0..15),
	betaOffset-RI-Index					INTEGER (0..15),
	betaOffset-CQI-Index				INTEGER (0..15)
}

PUSCH-ConfigDedicated-v1020 ::=		SEQUENCE {
	betaOffsetMC-r10					SEQUENCE {	
		betaOffset-ACK-Index-MC-r10			INTEGER (0..15),
		betaOffset-RI-Index-MC-r10			INTEGER (0..15),
		betaOffset-CQI-Index-MC-r10			INTEGER (0..15)
	}																		OPTIONAL,	-- Need OR
	groupHoppingDisabled-r10			ENUMERATED {true}					OPTIONAL,	-- Need OR
	dmrs-WithOCC-Activated-r10			ENUMERATED {true}					OPTIONAL	-- Need OR
}

PUSCH-ConfigDedicated-v1130 ::=		SEQUENCE {
	pusch-DMRS-r11						CHOICE {
		release								NULL,
		setup								SEQUENCE {
			nPUSCH-Identity-r11					INTEGER (0..509),
			nDMRS-CSH-Identity-r11				INTEGER (0..509)
		}
	}
}

PUSCH-ConfigDedicated-v1250::=			SEQUENCE {
	uciOnPUSCH				CHOICE {
		release					NULL,
		setup					SEQUENCE {
			betaOffset-ACK-Index-SubframeSet2-r12				INTEGER (0..15),
			betaOffset-RI-Index-SubframeSet2-r12				INTEGER (0..15),
			betaOffset-CQI-Index-SubframeSet2-r12				INTEGER (0..15),
			betaOffsetMC-r12					SEQUENCE {	
				betaOffset-ACK-Index-MC-SubframeSet2-r12			INTEGER (0..15),
				betaOffset-RI-Index-MC-SubframeSet2-r12			INTEGER (0..15),
				betaOffset-CQI-Index-MC-SubframeSet2-r12			INTEGER (0..15)
			}																OPTIONAL	-- Need OR
		}
	}
}

PUSCH-ConfigDedicated-v13xy ::=			SEQUENCE {
	betaOffset-r13								SEQUENCE {	
		betaOffset-ACK-Index-r13					INTEGER (0..15),
		betaOffset2-ACK-Index-r13					INTEGER (0..15)
	}																	OPTIONAL,	-- Need OR
	betaOffsetMC-r13							SEQUENCE {	
		betaOffset-ACK-Index-MC-r13					INTEGER (0..15),
		betaOffset2-ACK-Index-MC-r13				INTEGER (0..15)
	}																	OPTIONAL,	-- Need OR
	betaOffset-Subframeset2-r13					SEQUENCE {	
		betaOffset-ACK-Index-SubframeSet2-r13		INTEGER (0..15),
		betaOffset2-ACK-Index-SubframeSet2-r13		INTEGER (0..15)
	}																	OPTIONAL,	-- Need OR
	betaOffset-Subframeset2-MC-r13				SEQUENCE {	
		betaOffset-ACK-Index-MC-SubframeSet2-r13	INTEGER (0..15),
		betaOffset2-ACK-Index-MC-SubframeSet2-r13	INTEGER (0..15)
	}																	OPTIONAL	-- Need OR
}

PUSCH-ConfigDedicatedSCell-r10 ::=		SEQUENCE {
	groupHoppingDisabled-r10				ENUMERATED {true}				OPTIONAL,	-- Need OR
	dmrs-WithOCC-Activated-r10				ENUMERATED {true}				OPTIONAL	-- Need OR
}

UL-ReferenceSignalsPUSCH ::=		SEQUENCE {
	groupHoppingEnabled					BOOLEAN,
	groupAssignmentPUSCH				INTEGER (0..29),
	sequenceHoppingEnabled				BOOLEAN,
	cyclicShift							INTEGER (0..7)
}

-- ASN1STOP

PUSCH-Config field descriptions
betaOffset-ACK-Index, betaOffset-ACK-Index-MC
Parameter: , for single- and multiple-codeword respectively, see TS 36.213 [23, Table 8.6.3-1]. One value applies for all serving cells with an uplink and not configured with uplink power control subframe sets. The same value also applies for subframe set 1 of all serving cells with an uplink and configured with uplink power control subframe sets (the associated functionality is common i.e. not performed independently for each cell).
betaOffset-ACK-Index-SubframeSet2, betaOffset-ACK-Index-MC-SubframeSet2
Parameter: , for single- and multiple-codeword respectively, see TS 36.213 [23, Table 8.6.3-1]. One value applies for subframe set 2 of all serving cells with an uplink and configured with uplink power control subframe sets (the associated functionality is common i.e. not performed independently for each cell configured with uplink power control subframe sets).
betaOffset-CQI-Index, betaOffset-CQI-Index-MC
Parameter: , for single- and multiple-codeword respectively, see TS 36.213 [23, Table 8.6.3-3]. One value applies for all serving cells with an uplink and not configured with uplink power control subframe sets. The same value also applies for subframe set 1 of all serving cells with an uplink and configured with uplink power control subframe sets (the associated functionality is common i.e. not performed independently for each cell).
betaOffset-CQI-Index-SubframeSet2, betaOffset-CQI-Index-MC-SubframeSet2
Parameter: , for single- and multiple-codeword respectively, see TS 36.213 [23, Table 8.6.3-3]. One value applies for subframe set 2 of all serving cells with an uplink and configured with uplink power control subframe sets (the associated functionality is common i.e. not performed independently for each cell configured with uplink power control subframe sets).
betaOffset-RI-Index, betaOffset-RI-Index-MC
Parameter: , for single- and multiple-codeword respectively, see TS 36.213 [23, Table 8.6.3-2]. One value applies for all serving cells with an uplink and not configured with uplink power control subframe sets. The same value also applies for subframe set 1 of all serving cells with an uplink and configured with uplink power control subframe sets (the associated functionality is common i.e. not performed independently for each cell).
betaOffset-RI-Index-SubframeSet2, betaOffset-RI-Index-MC-SubframeSet2
Parameter: , for single- and multiple-codeword respectively, see TS 36.213 [23, Table 8.6.3-2]. One value applies for subframe set 2 of all serving cells with an uplink and configured with uplink power control subframe sets (the associated functionality is common i.e. not performed independently for each cell configured with uplink power control subframe sets).
cyclicShift
Parameters: cyclicShift, see TS 36.211 [21, Table 5.5.2.1.1-2].
dmrs-WithOCC-Activated
Parameter: Activate-DMRS-with OCC, see TS 36.211 [21, 5.5.2.1].
enable64QAM
See TS 36.213 [23, 8.6.1]. If enable64QAM (without suffix) is set to TRUE, it indicates that 64QAM is allowed for UE categories 5 and 8 indicated in ue-Category while FALSE indicates that 64QAM is not allowed. If enable64QAM-v1270 is set to TRUE, it indicates that 64QAM is allowed for UL categories 5 and 13 indicated in ue-CategoryUL. E-UTRAN configures enable64QAM-v1270 only when enable64QAM (without suffix) is set to TRUE.
groupAssignmentPUSCH
Parameter: ?SS See TS 36.211 [21, 5.5.1.3].
groupHoppingDisabled
Parameter: Disable-sequence-group-hopping, see TS 36.211 [21, 5.5.1.3].
groupHoppingEnabled
Parameter: Group-hopping-enabled, see TS 36.211 [21, 5.5.1.3].
hoppingMode
Parameter: Hopping-mode, see TS 36.211 [21, 5.3.4].
nDMRS-CSH-Identity 
Parameter: , see TS 36.211 [21, 5.5.2.1.1].
nPUSCH-Identity
Parameter: , see TS 36.211 [21, 5.5.1.5].
n-SB
Parameter: Nsb see TS 36.211 [21, 5.3.4].
pusch-hoppingOffset
Parameter: , see TS 36.211 [21, 5.3.4].
sequenceHoppingEnabled
Parameter: Sequence-hopping-enabled, see TS 36.211 [21, 5.5.1.4].
ul- ReferenceSignalsPUSCH
Used to specify parameters needed for the transmission on PUSCH (or PUCCH).

-	RACH-ConfigCommon
The IE RACH-ConfigCommon is used to specify the generic random access parameters.
RACH-ConfigCommon information element
-- ASN1START

RACH-ConfigCommon ::=		SEQUENCE {
	preambleInfo						SEQUENCE {
		numberOfRA-Preambles				ENUMERATED {
												n4, n8, n12, n16 ,n20, n24, n28,
												n32, n36, n40, n44, n48, n52, n56,
												n60, n64},
		preamblesGroupAConfig				SEQUENCE {
			sizeOfRA-PreamblesGroupA			ENUMERATED {
													n4, n8, n12, n16 ,n20, n24, n28,
													n32, n36, n40, n44, n48, n52, n56,
													n60},
			messageSizeGroupA					ENUMERATED {b56, b144, b208, b256},
			messagePowerOffsetGroupB			ENUMERATED {
													minusinfinity, dB0, dB5, dB8, dB10, dB12,
													dB15, dB18},
			...
		}			OPTIONAL													-- Need OP
	},
	powerRampingParameters				PowerRampingParameters,
	ra-SupervisionInfo					SEQUENCE {
		preambleTransMax					PreambleTransMax,
		ra-ResponseWindowSize				ENUMERATED {
												sf2, sf3, sf4, sf5, sf6, sf7,
												sf8, sf10},
		mac-ContentionResolutionTimer		ENUMERATED {
												sf8, sf16, sf24, sf32, sf40, sf48,
												sf56, sf64}
	},
	maxHARQ-Msg3Tx						INTEGER (1..8),
	...
}

RACH-ConfigCommon-v1250 ::=		SEQUENCE {
	txFailParams-r12 				SEQUENCE {
		connEstFailCount-r12					ENUMERATED {n1, n2, n3, n4},
		connEstFailOffsetValidity-r12			ENUMERATED {s30, s60, s120, s240, 
														s300, s420, s600, s900},
		connEstFailOffset-r12					INTEGER (0..15)		OPTIONAL	-- Need OP
	}
}

RACH-ConfigCommonSCell-r11 ::=		SEQUENCE {
	powerRampingParameters-r11				PowerRampingParameters,
	ra-SupervisionInfo-r11					SEQUENCE {
		preambleTransMax-r11					PreambleTransMax
	},
	...
}

PowerRampingParameters ::=			SEQUENCE {
	powerRampingStep					ENUMERATED {dB0, dB2,dB4, dB6},
	preambleInitialReceivedTargetPower	ENUMERATED {
											dBm-120, dBm-118, dBm-116, dBm-114, dBm-112,
											dBm-110, dBm-108, dBm-106, dBm-104, dBm-102,
											dBm-100, dBm-98, dBm-96, dBm-94,
											dBm-92, dBm-90}
}

PreambleTransMax ::=				ENUMERATED {
											n3, n4, n5, n6, n7,	n8, n10, n20, n50,
											n100, n200}

-- ASN1STOP

RACH-ConfigCommon field descriptions
connEstFailCount
Number of times that the UE detects T300 expiry on the same cell before applying connEstFailOffset. 
connEstFailOffset
Parameter "Qoffsettemp" in TS 36.304 [4]. If the field is not present the value of infinity shall be used for "Qoffsettemp".
connEstFailOffsetValidity
Amount of time that the UE applies connEstFailOffset before removing the offset from evaluation of the cell. Value s30 corresponds to 30 seconds, s60 corresponds to 60 seconds, and so on.
mac-ContentionResolutionTimer
Timer for contention resolution in TS 36.321 [6]. Value in subframes. Value sf8 corresponds to 8 subframes, sf16 corresponds to 16 subframes and so on.
maxHARQ-Msg3Tx
Maximum number of Msg3 HARQ transmissions in TS 36.321 [6], used for contention based random access. Value is an integer.
messagePowerOffsetGroupB
Threshold for preamble selection in TS 36.321 [6]. Value in dB. Value minusinfinity corresponds to -infinity. Value dB0 corresponds to 0 dB, dB5 corresponds to 5 dB and so on.
messageSizeGroupA
Threshold for preamble selection in TS 36.321 [6]. Value in bits. Value b56 corresponds to 56 bits, b144 corresponds to 144 bits and so on.
numberOfRA-Preambles
Number of non-dedicated random access preambles in TS 36.321 [6]. Value is an integer. Value n4 corresponds to 4, n8 corresponds to 8 and so on.
powerRampingStep
Power ramping factor in TS 36.321 [6]. Value in dB. Value dB0 corresponds to 0 dB, dB2 corresponds to 2 dB and so on.
preambleInitialReceivedTargetPower
Initial preamble power in TS 36.321 [6]. Value in dBm. Value dBm-120 corresponds to -120 dBm, dBm-118 corresponds to -118 dBm and so on.
preamblesGroupAConfig
Provides the configuration for preamble grouping in TS 36.321 [6]. If the field is not signalled, the size of the random access preambles group A [6] is equal to numberOfRA-Preambles.
preambleTransMax
Maximum number of preamble transmission in TS 36.321 [6]. Value is an integer. Value n3 corresponds to 3, n4 corresponds to 4 and so on.
ra-ResponseWindowSize
Duration of the RA response window in TS 36.321 [6]. Value in subframes. Value sf2 corresponds to 2 subframes, sf3 corresponds to 3 subframes and so on. The same value applies for each serving cell (although the associated functionality is performed independently for each cell).
sizeOfRA-PreamblesGroupA
Size of the random access preambles group A in TS 36.321 [6]. Value is an integer. Value n4 corresponds to 4, n8 corresponds to 8 and so on.

-	RACH-ConfigDedicated
The IE RACH-ConfigDedicated is used to specify the dedicated random access parameters.
RACH-ConfigDedicated information element
-- ASN1START

RACH-ConfigDedicated ::=		SEQUENCE {
	ra-PreambleIndex					INTEGER (0..63),
	ra-PRACH-MaskIndex					INTEGER (0..15)
}

-- ASN1STOP

RACH-ConfigDedicated field descriptions
ra-PRACH-MaskIndex
Explicitly signalled PRACH Mask Index for RA Resource selection in TS 36.321 [6].
ra-PreambleIndex
Explicitly signalled Random Access Preamble for RA Resource selection in TS 36.321 [6].

-	RadioResourceConfigCommon
The IE RadioResourceConfigCommonSIB and IE RadioResourceConfigCommon are used to specify common radio resource configurations in the system information and in the mobility control information, respectively, e.g., the random access parameters and the static physical layer parameters.
RadioResourceConfigCommon information element
-- ASN1START

RadioResourceConfigCommonSIB ::=	SEQUENCE {
	rach-ConfigCommon					RACH-ConfigCommon,
	bcch-Config 						BCCH-Config,
	pcch-Config 						PCCH-Config,
	prach-Config						PRACH-ConfigSIB,
	pdsch-ConfigCommon					PDSCH-ConfigCommon,
	pusch-ConfigCommon					PUSCH-ConfigCommon,
	pucch-ConfigCommon					PUCCH-ConfigCommon,
	soundingRS-UL-ConfigCommon			SoundingRS-UL-ConfigCommon,
	uplinkPowerControlCommon			UplinkPowerControlCommon,
	ul-CyclicPrefixLength				UL-CyclicPrefixLength,
	...,
	[[	uplinkPowerControlCommon-v1020	UplinkPowerControlCommon-v1020		OPTIONAL	-- Need OR
	]],
	[[	rach-ConfigCommon-v1250			RACH-ConfigCommon-v1250		OPTIONAL	-- Need OR
	]],
	[[	pusch-ConfigCommon-v1270		PUSCH-ConfigCommon-v1270		OPTIONAL		-- Need OR
	]]
}

RadioResourceConfigCommon ::=		SEQUENCE {
	rach-ConfigCommon					RACH-ConfigCommon					OPTIONAL,	-- Need ON
	prach-Config						PRACH-Config,
	pdsch-ConfigCommon					PDSCH-ConfigCommon					OPTIONAL,	-- Need ON
	pusch-ConfigCommon					PUSCH-ConfigCommon,
	phich-Config						PHICH-Config						OPTIONAL,	-- Need ON
	pucch-ConfigCommon					PUCCH-ConfigCommon					OPTIONAL,	-- Need ON
	soundingRS-UL-ConfigCommon			SoundingRS-UL-ConfigCommon			OPTIONAL,	-- Need ON
	uplinkPowerControlCommon			UplinkPowerControlCommon			OPTIONAL,	-- Need ON
	antennaInfoCommon					AntennaInfoCommon			OPTIONAL,	-- Need ON
	p-Max								P-Max								OPTIONAL,	-- Need OP
	tdd-Config							TDD-Config							OPTIONAL,	-- Cond TDD
	ul-CyclicPrefixLength				UL-CyclicPrefixLength,
	...,
	[[	uplinkPowerControlCommon-v1020	UplinkPowerControlCommon-v1020		OPTIONAL	-- Need ON
	]],
	[[	tdd-Config-v1130				TDD-Config-v1130				OPTIONAL	-- Cond TDD3
	]],
	[[	pusch-ConfigCommon-v1270		PUSCH-ConfigCommon-v1270		OPTIONAL		-- Need OR
	]],
	[[	uplinkPowerControlCommon-v13xy	UplinkPowerControlCommon-v13xy		OPTIONAL	-- Need ON
	]]
}

RadioResourceConfigCommonPSCell-r12 ::=	SEQUENCE {
	basicFields-r12						RadioResourceConfigCommonSCell-r10,
	pucch-ConfigCommon-r12				PUCCH-ConfigCommon,
	rach-ConfigCommon-r12				RACH-ConfigCommon,
	uplinkPowerControlCommonPSCell-r12	UplinkPowerControlCommonPSCell-r12,
	...,
	[[	uplinkPowerControlCommon-v13xy	UplinkPowerControlCommon-v13xy		OPTIONAL	-- Need ON
	]]
}

RadioResourceConfigCommonSCell-r10 ::=	SEQUENCE {
	-- DL configuration as well as configuration applicable for DL and UL
	nonUL-Configuration-r10					SEQUENCE {
		-- 1: Cell characteristics
		dl-Bandwidth-r10						ENUMERATED {n6, n15, n25, n50, n75, n100},
		-- 2: Physical configuration, general
		antennaInfoCommon-r10					AntennaInfoCommon,
		mbsfn-SubframeConfigList-r10			MBSFN-SubframeConfigList	OPTIONAL,	-- Need OR
		-- 3: Physical configuration, control
		phich-Config-r10						PHICH-Config,
		-- 4: Physical configuration, physical channels
		pdsch-ConfigCommon-r10					PDSCH-ConfigCommon,
		tdd-Config-r10							TDD-Config					OPTIONAL	-- Cond TDDSCell
	},
	-- UL configuration
	ul-Configuration-r10						SEQUENCE {
		ul-FreqInfo-r10						SEQUENCE {
			ul-CarrierFreq-r10					ARFCN-ValueEUTRA			OPTIONAL,	-- Need OP
			ul-Bandwidth-r10					ENUMERATED {n6, n15,
													n25, n50, n75, n100}	OPTIONAL,	-- Need OP
			additionalSpectrumEmissionSCell-r10		AdditionalSpectrumEmission
		},
		p-Max-r10							P-Max						OPTIONAL,	-- Need OP
		uplinkPowerControlCommonSCell-r10		UplinkPowerControlCommonSCell-r10,
		-- A special version of IE UplinkPowerControlCommon may be introduced
		-- 3: Physical configuration, control
		soundingRS-UL-ConfigCommon-r10		SoundingRS-UL-ConfigCommon,
		ul-CyclicPrefixLength-r10			UL-CyclicPrefixLength,
		-- 4: Physical configuration, physical channels
		prach-ConfigSCell-r10					PRACH-ConfigSCell-r10		OPTIONAL,	-- Cond TDD-OR-NoR11
		pusch-ConfigCommon-r10				PUSCH-ConfigCommon
	}																	OPTIONAL,	-- Need OR
	...,
	[[	ul-CarrierFreq-v1090				ARFCN-ValueEUTRA-v9e0			OPTIONAL	-- Need OP
	]],
	[[	rach-ConfigCommonSCell-r11			RACH-ConfigCommonSCell-r11		OPTIONAL,	-- Cond ULSCell
		prach-ConfigSCell-r11				PRACH-Config					OPTIONAL,	-- Cond UL
		tdd-Config-v1130					TDD-Config-v1130			OPTIONAL,	-- Cond TDD2
		uplinkPowerControlCommonSCell-v1130
								UplinkPowerControlCommonSCell-v1130	OPTIONAL	-- Cond UL
	]],
	[[	pusch-ConfigCommon-v1270		PUSCH-ConfigCommon-v1270		OPTIONAL		-- Need OR
	]],
	[[	pucch-ConfigCommon-r13				PUCCH-ConfigCommon		OPTIONAL,	-- Cond UL
		uplinkPowerControlCommonSCell-v13xx	UplinkPowerControlCommonPSCell-r12	OPTIONAL	-- Cond UL
	]]
}

BCCH-Config ::=						SEQUENCE {
	modificationPeriodCoeff				ENUMERATED {n2, n4, n8, n16}
}

PCCH-Config ::=						SEQUENCE {
	defaultPagingCycle					ENUMERATED {
											rf32, rf64, rf128, rf256},
	nB									ENUMERATED {
											fourT, twoT, oneT, halfT, quarterT, oneEighthT,
											oneSixteenthT, oneThirtySecondT}
}

UL-CyclicPrefixLength ::=			ENUMERATED {len1, len2}

-- ASN1STOP

RadioResourceConfigCommon field descriptions
additionalSpectrumEmissionSCell
The UE requirements related to additionalSpectrumEmissionSCell are defined in TS 36.101 [42]. E-UTRAN configures the same value in additionalSpectrumEmissionSCell for all SCell(s) of the same band with UL configured. The additionalSpectrumEmissionSCell is applicable for all serving cells (including PCell) of the same band with UL configured.
defaultPagingCycle
Default paging cycle, used to derive 'T' in TS 36.304 [4]. Value rf32 corresponds to 32 radio frames, rf64 corresponds to 64 radio frames and so on.
modificationPeriodCoeff
Actual modification period, expressed in number of radio frames= modificationPeriodCoeff * defaultPagingCycle. n2 corresponds to value 2, n4 corresponds to value 4, n8 corresponds to value 8 and n16 corresponds to value 16.
nB
Parameter: nB is used as one of parameters to derive the Paging Frame and Paging Occasion according to TS 36.304 [4]. Value in multiples of 'T' as defined in TS 36.304 [4]. A value of fourT corresponds to 4 * T, a value of twoT corresponds to 2 * T and so on.
p-Max
Pmax to be used in the target cell. If absent the UE applies the maximum power according to the UE capability.
ul-Bandwidth
Parameter: transmission bandwidth configuration, NRB, in uplink, see TS 36.101 [42, table 5.6-1]. Value n6 corresponds to 6 resource blocks, n15 to 15 resource blocks and so on. If for FDD this parameter is absent, the uplink bandwidth is equal to the downlink bandwidth. For TDD this parameter is absent and it is equal to the downlink bandwidth.
ul-CarrierFreq
For FDD: If absent, the (default) value determined from the default TX-RX frequency separation defined in TS 36.101 [42, table 5.7.3-1] applies.
For TDD: This parameter is absent and it is equal to the downlink frequency.
UL-CyclicPrefixLength
Parameter: Uplink cyclic prefix length see 36.211 [21, 5.2.1] where len1 corresponds to normal cyclic prefix and len2 corresponds to extended cyclic prefix.

Conditional presence
Explanation
TDD
The field is optional for TDD, Need ON; it is not present for FDD and the UE shall delete any existing value for this field.
TDD2
If tdd-Config-r10 is present, the field is optional, Need OR. Otherwise the field is not present and the UE shall delete any existing value for this field.
TDD3
If tdd-Config is present, the field is optional, Need OR. Otherwise the field is not present and the UE shall delete any existing value for this field.
TDD-OR-NoR11
If prach-ConfigSCell-r11 is absent, the field is optional for TDD, Need OR. Otherwise the field is not present and the UE shall delete any existing value for this field.
TDDSCell
This field is mandatory present for TDD; it is not present for FDD and the UE shall delete any existing value for this field.
UL
If the SCell is part of the STAG or concerns the PSCell and if ul-Configuration is included, the field is optional, Need OR. Otherwise the field is not present and the UE shall delete any existing value for this field.
ULSCell
For the PSCell (IE is included in RadioResourceConfigCommonPSCell) the field is absent. Otherwise, if the SCell is part of the STAG and if ul-Configuration is included, the field is optional, Need OR. Otherwise the field is not present and the UE shall delete any existing value for this field.

-	RadioResourceConfigDedicated
The IE RadioResourceConfigDedicated is used to setup/modify/release RBs, to modify the MAC main configuration, to modify the SPS configuration and to modify dedicated physical configuration.
RadioResourceConfigDedicated information element
-- ASN1START

RadioResourceConfigDedicated ::=		SEQUENCE {
	srb-ToAddModList					SRB-ToAddModList			OPTIONAL, 		-- Cond HO-Conn
	drb-ToAddModList					DRB-ToAddModList			OPTIONAL, 		-- Cond HO-toEUTRA
	drb-ToReleaseList					DRB-ToReleaseList			OPTIONAL, 		-- Need ON
	mac-MainConfig						CHOICE {
			explicitValue					MAC-MainConfig,
			defaultValue					NULL
	}		OPTIONAL,																-- Cond HO-toEUTRA2
	sps-Config							SPS-Config 					OPTIONAL,		-- Need ON
	physicalConfigDedicated				PhysicalConfigDedicated		OPTIONAL,		-- Need ON
	...,
	[[	rlf-TimersAndConstants-r9		RLF-TimersAndConstants-r9			OPTIONAL	-- Need ON
	]],
	[[	measSubframePatternPCell-r10	MeasSubframePatternPCell-r10		OPTIONAL	-- Need ON
	]],
	[[	neighCellsCRS-Info-r11			NeighCellsCRS-Info-r11				OPTIONAL	-- Need ON
	]],
	[[	naics-Info-r12				NAICS-AssistanceInfo-r12			OPTIONAL	-- Need ON
	]],
	[[	neighCellsCRS-Info-r13			NeighCellsCRS-Info-r13				OPTIONAL	-- Cond CRSIM
	]]
}

RadioResourceConfigDedicatedPSCell-r12 ::=		SEQUENCE {
	-- UE specific configuration extensions applicable for an PSCell
	physicalConfigDedicatedPSCell-r12		PhysicalConfigDedicated		OPTIONAL,	-- Need ON
	sps-Config-r12							SPS-Config					OPTIONAL,	-- Need ON
	naics-Info-r12							NAICS-AssistanceInfo-r12	OPTIONAL,	-- Need ON
	...,
	[[	neighCellsCRS-InfoPSCell-r13		NeighCellsCRS-Info-r13		OPTIONAL	-- Need ON
	]]
}

RadioResourceConfigDedicatedSCG-r12 ::=		SEQUENCE {
	drb-ToAddModListSCG-r12				DRB-ToAddModListSCG-r12			OPTIONAL, 	-- Need ON
	mac-MainConfigSCG-r12				MAC-MainConfig					OPTIONAL,	-- Need ON
	rlf-TimersAndConstantsSCG-r12		RLF-TimersAndConstantsSCG-r12	OPTIONAL,	-- Need ON
	...
}

RadioResourceConfigDedicatedSCell-r10 ::=	SEQUENCE {
	-- UE specific configuration extensions applicable for an SCell
	physicalConfigDedicatedSCell-r10		PhysicalConfigDedicatedSCell-r10	OPTIONAL,	-- Need ON
	...,
	[[	mac-MainConfigSCell-r11			MAC-MainConfigSCell-r11			OPTIONAL	-- Cond SCellAdd
	]],
	[[	naics-Info-r12				NAICS-AssistanceInfo-r12		OPTIONAL	-- Need ON
	]],
	[[	neighCellsCRS-InfoSCell-r13			NeighCellsCRS-Info-r13		OPTIONAL	-- Need ON
	]]

}

SRB-ToAddModList ::=				SEQUENCE (SIZE (1..2)) OF SRB-ToAddMod

SRB-ToAddMod ::=	SEQUENCE {
	srb-Identity						INTEGER (1..2),
	rlc-Config							CHOICE {
		explicitValue						RLC-Config,
		defaultValue						NULL
	}		OPTIONAL,																-- Cond Setup
	logicalChannelConfig				CHOICE {
		explicitValue						LogicalChannelConfig,
		defaultValue						NULL
	}		OPTIONAL,																-- Cond Setup
	...
}

DRB-ToAddModList ::=				SEQUENCE (SIZE (1..maxDRB)) OF DRB-ToAddMod

DRB-ToAddModListSCG-r12 ::=		SEQUENCE (SIZE (1..maxDRB)) OF DRB-ToAddModSCG-r12

DRB-ToAddMod ::=	SEQUENCE {
	eps-BearerIdentity					INTEGER (0..15)			OPTIONAL,		-- Cond DRB-Setup
	drb-Identity						DRB-Identity,
	pdcp-Config							PDCP-Config				OPTIONAL,		-- Cond PDCP
	rlc-Config							RLC-Config				OPTIONAL,		-- Cond SetupM
	logicalChannelIdentity				INTEGER (3..10)			OPTIONAL,		-- Cond DRB-SetupM
	logicalChannelConfig				LogicalChannelConfig	OPTIONAL,		-- Cond SetupM
	...,
	[[	drb-TypeChange-r12						ENUMERATED {toMCG}	OPTIONAL,		-- Need OP
		rlc-Config-v1250					RLC-Config-v1250		OPTIONAL		-- Need ON
	]],
	[[	rlc-Config-v13xx					RLC-Config-v13xx		OPTIONAL		-- Need ON
	]]
}

DRB-ToAddModSCG-r12 ::=	SEQUENCE {
	drb-Identity-r12					DRB-Identity,
	drb-Type-r12						CHOICE {
		split-r12							NULL,
		scg-r12								SEQUENCE {
			eps-BearerIdentity-r12				INTEGER (0..15)	OPTIONAL,	-- Cond DRB-Setup
			pdcp-Config-r12						PDCP-Config		OPTIONAL	-- Cond PDCP-S
		}
	}															OPTIONAL,	-- Cond SetupS2
	rlc-ConfigSCG-r12					RLC-Config				OPTIONAL,	-- Cond SetupS
	rlc-Config-v1250						RLC-Config-v1250			OPTIONAL,	-- Need ON
	logicalChannelIdentitySCG-r12		INTEGER (3..10)			OPTIONAL,	-- Cond DRB-SetupS
	logicalChannelConfigSCG-r12			LogicalChannelConfig	OPTIONAL,	-- Cond SetupS
	...
}

DRB-ToReleaseList ::=				SEQUENCE (SIZE (1..maxDRB)) OF DRB-Identity

MeasSubframePatternPCell-r10 ::=		CHOICE {
	release								NULL,
	setup							MeasSubframePattern-r10
}

NeighCellsCRS-Info-r11 ::=		CHOICE {
	release							NULL,
	setup							CRS-AssistanceInfoList-r11
}

CRS-AssistanceInfoList-r11 ::=	SEQUENCE (SIZE (1..maxCellReport)) OF CRS-AssistanceInfo-r11

CRS-AssistanceInfo-r11 ::= SEQUENCE {
	physCellId-r11						PhysCellId,
	antennaPortsCount-r11				ENUMERATED {an1, an2, an4, spare1},
	mbsfn-SubframeConfigList-r11		MBSFN-SubframeConfigList,
	...
}

NeighCellsCRS-Info-r13 ::=		CHOICE {
	release							NULL,
	setup							CRS-AssistanceInfoList-r13
}

CRS-AssistanceInfoList-r13 ::=	SEQUENCE (SIZE (1..maxCellReport)) OF CRS-AssistanceInfo-r13

CRS-AssistanceInfo-r13 ::= SEQUENCE {
	physCellId-r13						PhysCellId,
	antennaPortsCount-r13				ENUMERATED {an1, an2, an4, spare1},
	mbsfn-SubframeConfigList-r13		MBSFN-SubframeConfigList	OPTIONAL,	-- Need ON
	...
}

NAICS-AssistanceInfo-r12 ::=		CHOICE {
	release							NULL,
	setup							SEQUENCE {
		neighCellsToReleaseList-r12		NeighCellsToReleaseList-r12			OPTIONAL	,	-- Need ON
		neighCellsToAddModList-r12		NeighCellsToAddModList-r12			OPTIONAL,	-- Need ON
		servCellp-a-r12					P-a	 							OPTIONAL	-- Need ON
	}
}

NeighCellsToReleaseList-r12 ::=	SEQUENCE (SIZE (1..maxNeighCell-r12)) OF PhysCellId

NeighCellsToAddModList-r12 ::=	SEQUENCE (SIZE (1..maxNeighCell-r12)) OF NeighCellsInfo-r12

NeighCellsInfo-r12	::=		SEQUENCE {
	physCellId-r12					PhysCellId,
	p-b-r12						INTEGER (0..3),
	crs-PortsCount-r12				ENUMERATED {n1, n2, n4, spare},
	mbsfn-SubframeConfig-r12		MBSFN-SubframeConfigList				OPTIONAL,	-- Need ON
	p-aList-r12					SEQUENCE (SIZE (1..maxP-a-PerNeighCell-r12)) OF P-a,
	transmissionModeList-r12		BIT STRING (SIZE(8)),
	resAllocGranularity-r12			INTEGER (1..4),
	...
}
P-a ::= ENUMERATED {	dB-6, dB-4dot77, dB-3, dB-1dot77,
									dB0, dB1, dB2, dB3}

-- ASN1STOP

RadioResourceConfigDedicated field descriptions
crs-PortsCount
Parameter represents the number of antenna ports for cell-specific reference signal used by the signaled neighboring cell where n1 corresponds to 1 antenna port, n2 to 2 antenna ports etc. see TS 36.211 [21, 6.10.1].
drb-Identity
In case of DC, the DRB identity is unique within the scope of the UE i.e. an SCG DRB can not use the same value as used for an MCG or split DRB. For a split DRB the same identity is used for the MCG- and SCG parts of the configuration.
drb-ToAddModListSCG
When an SCG is configured, E-UTRAN configures at least one SCG or split DRB.
drb-Type
This field indicates whether the DRB is split or SCG DRB. E-UTRAN does not configure split and SCG DRBs simultaneously for the UE.
drb-TypeChange
Indicates that a split/SCG DRB is reconfigured to an MCG DRB (i.e. E-UTRAN only signals the field in case the DRB type changes).
logicalChannelConfig
For SRBs a choice is used to indicate whether the logical channel configuration is signalled explicitly or set to the default logical channel configuration for SRB1 as specified in 9.2.1.1 or for SRB2 as specified in 9.2.1.2.
logicalChannelIdentity
The logical channel identity for both UL and DL.
mac-MainConfig
Although the ASN.1 includes a choice that is used to indicate whether the mac-MainConfig is signalled explicitly or set to the default MAC main configuration as specified in 9.2.2, EUTRAN does not apply "defaultValue".
mbsfn-SubframeConfig
Defines the MBSFN subframe configuration used by the signaled neighboring cell. If absent, UE assumes no MBSFN configuration for the neighboring cell.
measSubframePatternPCell
Time domain measurement resource restriction pattern for the PCell measurements (RSRP, RSRQ and the radio link monitoring).
neighCellsCRS-Info, neighCellsCRS-InfoSCell, neighCellsCRS-InfoPSCell
This field contains assistance information used by the UE to mitigate interference from CRS while performing RRM/RLM/CSI measurement or data demodulation. When the received CRS assistance information is for a cell with CRS non-colliding with that of the CRS of the cell to measure, the UE may use the CRS assistance information to mitigate CRS interference. When the received CRS assistance information is for a cell with CRS colliding with that of the CRS of the cell to measure, the UE may use the CRS assistance information to mitigate CRS interference RRM/RLM (as specified in TS 36.133 [16]) and for CSI (as specified in TS 36.101 [42]) on the subframes indicated by measSubframePatternPCell, measSubframePatternConfigNeigh, csi-MeasSubframeSet1 if configured, and the CSI subframe set 1 if csi-MeasSubframeSets-r12 is configured. The UE may use CRS assistance information to mitigate CRS interference from the cells in the CRS-AssistanceInfoList for the demodulation purpose as specified in TS 36.101 [42]. EUTRAN does not configure neighCellsCRS-Info-r11 or neighCellsCRS-Info-r13 if eimta-MainConfigPCell-r12 is configured.
neighCellsToAddModList
This field contains assistance information used by the UE to cancel and suppress interference of a neighbouring cell. If this field is present for a neighbouring cell, the UE assumes that the transmission parameters listed in the sub-fields are used by the neighbouring cell. If this field is present for a neighbouring cell, the UE assumes the neighbour cell is subframe and SFN synchronized to the serving cell, has the same system bandwidth, UL/DL and special subframe configuration, and cyclic prefix length as the serving cell.
p-aList
Indicates the restricted subset of power offset for QPSK, 16QAM, and 64QAM PDSCH transmissions for the neighbouring cell by using the parameter, see TS 36.213 [23, 5.2]. Value dB-6 corresponds to -6 dB, dB-4dot77 corresponds to -4.77 dB etc.
p-b
Parameter: , indicates the cell-specific ratio used by the signaled neighboring cell, see TS 36.213 [23, Table 5.2-1].
physicalConfigDedicated
The default dedicated physical configuration is specified in 9.2.4.
resAllocGranularity
Indicates the resource allocation and precoding granularity in PRB pair level of the signaled neighboring cell, see TS 36.213 [23, 7.1.6].
rlc-Config
For SRBs a choice is used to indicate whether the RLC configuration is signalled explicitly or set to the values defined in the default RLC configuration for SRB1 in 9.2.1.1 or for SRB2 in 9.2.1.2. RLC AM is the only applicable RLC mode for SRB1 and SRB2. E-UTRAN does not reconfigure the RLC mode of DRBs except when a full configuration option is used, and may reconfigure the RLC SN field size and the AM RLC LI field size only upon handover within E-UTRA or upon the first reconfiguration after RRC connection re-establishment or upon SCG Change for SCG and split DRBs.
servCellp-a
Indicates the power offset for QPSK C-RNTI based PDSCH transmissions used by the serving cell, see 36.213 [23, 5.2]. Value dB-6 corresponds to -6 dB, dB-4dot77 corresponds to -4.77 dB etc.
sps-Config
The default SPS configuration is specified in 9.2.3. Except for handover or releasing SPS for MCG, E-UTRAN does not reconfigure sps-Config for MCG when there is a configured downlink assignment or a configured uplink grant for MCG (see TS 36.321 [6]). Except for SCG change or releasing SPS for SCG, E-UTRAN does not reconfigure sps-Config for SCG when there is a configured downlink assignment or a configured uplink grant for SCG (see TS 36.321 [6]).
srb-Identity
Value 1 is applicable for SRB1 only.
Value 2 is applicable for SRB2 only.
transmissionModeList
Indicates a subset of transmission mode 1, 2, 3, 4, 6, 8, 9, 10, for the signaled neighboring cell for which NeighCellsInfo applies. When TM10 is signaled, other signaled transmission parameters in NeighCellsInfo are not applicable to up to 8 layer transmission scheme of TM10. E-UTRAN may indicate TM9 when TM10 with QCL type A and DMRS scrambling with  in TS 36.211 [21, 6.10.3.1] is used in the signalled neighbour cell and TM9 or TM10 with QCL type A and DMRS scrambling with  in TS 36.211 [21, 6.10.3.1] is used in the serving cell. UE behaviour with NAICS when TM10 is used is only defined when QCL type A and DMRS scrambling with  in TS 36.211 [21, 6.10.3.1] is used for the serving cell and all signalled neighbour cells. The first/ leftmost bit is for transmission mode 1, the second bit is for transmission mode 2, and so on.

Conditional presence
Explanation
CRSIM
The field is optionally present, need ON, if neighCellsCRS-Info-r11 is not present; otherwise it is not present.
DRB-Setup
The field is mandatory present if the corresponding DRB is being set up; otherwise it is not present.
DRB-SetupM
The field is mandatory present upon setup of MCG or split DRB; The field is optionally present, Need ON, upon change from SCG to MCG DRB; otherwise it is not present.
DRB-SetupS
The field is mandatory present upon setup of SCG or split DRB, or upon change from MCG to split DRB; The field is optionally present, Need ON, upon change from MCG to SCG DRB; otherwise it is not present.
HO-Conn
The field is mandatory present in case of handover to E-UTRA or when the fullConfig is included in the RRCConnectionReconfiguration message or in case of RRC connection establishment; otherwise the field is optionally present, need ON. Upon connection establishment/ re-establishment only SRB1 is applicable.
HO-toEUTRA
The field is mandatory present in case of handover to E-UTRA or when the fullConfig is included in the RRCConnectionReconfiguration message; In case of RRC connection establishment and RRC connection re-establishment the field is not present; otherwise the field is optionally present, need ON.
HO-toEUTRA2
The field is mandatory present in case of handover to E-UTRA or when the fullConfig is included in the RRCConnectionReconfiguration message; otherwise the field is optionally present, need ON.
PDCP
The field is mandatory present if the corresponding DRB is being setup; the field is optionally present, need ON, upon reconfiguration of the corresponding split DRB, upon the corresponding DRB type change from split to MCG bearer, upon the corresponding DRB type change from MCG to split bearer, upon handover within E-UTRA and upon the first reconfiguration after re-establishment but in all these cases only when fullConfig is not included in the RRCConnectionReconfiguration message; otherwise it is not present.
PDCP-S
The field is mandatory present if the corresponding DRB is being setup; the field is optionally present, need ON, upon SCG change; otherwise it is not present.
RLC-Setup
This field is optionally present if the corresponding DRB is being setup, need ON; otherwise it is not present.
SCellAdd
The field is optionally present, need ON, upon SCell addition; otherwise it is not present.
Setup
The field is mandatory present if the corresponding SRB/DRB is being setup; otherwise the field is optionally present, need ON.
SetupM
The field is mandatory present upon setup of an MCG or split DRB; otherwise the field is optionally present, need ON.
SetupS
The field is mandatory present upon setup of an SCG or split DRB, as well as upon change from MCG to split DRB; otherwise the field is optionally present, need ON.
SetupS2
The field is mandatory present upon setup of an SCG or split DRB, as well as upon change from MCG to split or SCG DRB. For an SCG DRB the field is optionally present, need ON. Otherwise the field is not present.

-	RLC-Config
The IE RLC-Config is used to specify the RLC configuration of SRBs and DRBs.
RLC-Config information element
-- ASN1START

RLC-Config ::=				CHOICE {
	am									SEQUENCE {
		ul-AM-RLC							UL-AM-RLC,
		dl-AM-RLC							DL-AM-RLC
	},
	um-Bi-Directional					SEQUENCE {
		ul-UM-RLC							UL-UM-RLC,
		dl-UM-RLC							DL-UM-RLC
	},
	um-Uni-Directional-UL				SEQUENCE {
		ul-UM-RLC							UL-UM-RLC
	},
	um-Uni-Directional-DL				SEQUENCE {
		dl-UM-RLC							DL-UM-RLC
	},
	...
}

RLC-Config-v1250 ::=				SEQUENCE {
	ul-extended-RLC-LI-Field-r12			BOOLEAN,
	dl-extended-RLC-LI-Field-r12			BOOLEAN
}

RLC-Config-v13xx ::=				SEQUENCE {
	ul-extended-RLC-AM-SN-r13 					BOOLEAN,
	dl-extended-RLC-AM-SN-r13 					BOOLEAN,
	pollPDU-v13xy								PollPDU-v13xy		OPTIONAL   -- Need OR
}

UL-AM-RLC ::=						SEQUENCE {
	t-PollRetransmit					T-PollRetransmit,
	pollPDU								PollPDU,
	pollByte							PollByte,
	maxRetxThreshold					ENUMERATED {
											t1, t2, t3, t4, t6, t8, t16, t32}
}

DL-AM-RLC ::=						SEQUENCE {
	t-Reordering						T-Reordering,
	t-StatusProhibit					T-StatusProhibit
}

UL-UM-RLC ::=						SEQUENCE {
	sn-FieldLength						SN-FieldLength
}

DL-UM-RLC ::=						SEQUENCE {
	sn-FieldLength						SN-FieldLength,
	t-Reordering						T-Reordering
}

SN-FieldLength ::=					ENUMERATED {size5, size10}

T-PollRetransmit ::=				ENUMERATED {
										ms5, ms10, ms15, ms20, ms25, ms30, ms35,
										ms40, ms45, ms50, ms55, ms60, ms65, ms70,
										ms75, ms80, ms85, ms90, ms95, ms100, ms105,
										ms110, ms115, ms120, ms125, ms130, ms135,
										ms140, ms145, ms150, ms155, ms160, ms165,
										ms170, ms175, ms180, ms185, ms190, ms195,
										ms200, ms205, ms210, ms215, ms220, ms225,
										ms230, ms235, ms240, ms245, ms250, ms300,
										ms350, ms400, ms450, ms500, spare9, spare8,
										spare7, spare6, spare5, spare4, spare3,
										spare2, spare1}

PollPDU ::=							ENUMERATED {
										p4, p8, p16, p32, p64, p128, p256, pInfinity}

PollPDU-v13xy ::=					ENUMERATED {
										p512, p1024, p2048, p4096, p6144, p8192, p12288, p16384}

PollByte ::=						ENUMERATED {
										kB25, kB50, kB75, kB100, kB125, kB250, kB375,
										kB500, kB750, kB1000, kB1250, kB1500, kB2000,
										kB3000, kBinfinity, spare1}

T-Reordering ::=					ENUMERATED {
										ms0, ms5, ms10, ms15, ms20, ms25, ms30, ms35,
										ms40, ms45, ms50, ms55, ms60, ms65, ms70,
										ms75, ms80, ms85, ms90, ms95, ms100, ms110,
										ms120, ms130, ms140, ms150, ms160, ms170,
										ms180, ms190, ms200, spare1}

T-StatusProhibit ::=				ENUMERATED {
										ms0, ms5, ms10, ms15, ms20, ms25, ms30, ms35,
										ms40, ms45, ms50, ms55, ms60, ms65, ms70,
										ms75, ms80, ms85, ms90, ms95, ms100, ms105,
										ms110, ms115, ms120, ms125, ms130, ms135,
										ms140, ms145, ms150, ms155, ms160, ms165,
										ms170, ms175, ms180, ms185, ms190, ms195,
										ms200, ms205, ms210, ms215, ms220, ms225,
										ms230, ms235, ms240, ms245, ms250, ms300,
										ms350, ms400, ms450, ms500, spare8, spare7,
										spare6, spare5, spare4, spare3, spare2,
										spare1}

-- ASN1STOP

RLC-Config field descriptions
dl-extended-RLC-LI-Field, ul-extended-RLC-LI-Field
Indicates the RLC LI field size. Value TRUE means that 15 bit LI length shall be used, otherwise 11 bit LI length shall be used; see TS 36.322 [7]. E-UTRAN enables this field only when RLC-Config (without suffix) is set to am.
maxRetxThreshold
Parameter for RLC AM in TS 36.322 [7]. Value t1 corresponds to 1 retransmission, t2 to 2 retransmissions and so on.
pollByte
Parameter for RLC AM in TS 36.322 [7]. Value kB25 corresponds to 25 kBytes, kB50 to 50 kBytes and so on. kBInfinity corresponds to an infinite amount of kBytes.
pollPDU
Parameter for RLC AM in TS 36.322 [7]. Value p4 corresponds to 4 PDUs, p8 to 8 PDUs and so on. pInfinity corresponds to an infinite number of PDUs. In case pollPDU-r13 is signalled, the UE shall ignore pollPDU (i.e. without suffix). E-UTRAN enables pollPDU-v13xy field only when RLC-Config (without suffix) is set to am.
sn-FieldLength
Indicates the UM RLC SN field size, see TS 36.322 [7], in bits. Value size5 means 5 bits, size10 means 10 bits.
t-PollRetransmit
Timer for RLC AM in TS 36.322 [7], in milliseconds. Value ms5 means 5ms, ms10 means 10ms and so on.
t-Reordering
Timer for reordering in TS 36.322 [7], in milliseconds. Value ms0 means 0ms, ms5 means 5ms and so on.
t-StatusProhibit
Timer for status reporting in TS 36.322 [7], in milliseconds. Value ms0 means 0ms, ms5 means 5ms and so on.
ul-extended-RLC-AM-SN, dl-extended-RLC-AM-SN
Indicates whether or not the UE shall use the exteneded SN and SO length for AM bearer. Value TRUE means that 16 bit SN length and 16 bit SO length shall be used, otherwise 10 bit SN length and 15 bit SO length shall be used; see TS 36.322 [7].

-	RLF-TimersAndConstants
The IE RLF-TimersAndConstants contains UE specific timers and constants applicable for UEs in RRC_CONNECTED.
RLF-TimersAndConstants information element
-- ASN1START

RLF-TimersAndConstants-r9 ::=			CHOICE {
	release									NULL,
	setup									SEQUENCE {
		t301-r9								ENUMERATED {
												ms100, ms200, ms300, ms400, ms600, ms1000, ms1500,
												ms2000},
		t310-r9								ENUMERATED {
												ms0, ms50, ms100, ms200, ms500, ms1000, ms2000},
		n310-r9								ENUMERATED {
												n1, n2, n3, n4, n6, n8, n10, n20},
		t311-r9								ENUMERATED {
												ms1000, ms3000, ms5000, ms10000, ms15000,
												ms20000, ms30000},
		n311-r9								ENUMERATED {
												n1, n2, n3, n4, n5, n6, n8, n10},
		...
	}
}

RLF-TimersAndConstantsSCG-r12 ::=			CHOICE {
	release								NULL,
	setup								SEQUENCE {
		t313-r12							ENUMERATED {
												ms0, ms50, ms100, ms200, ms500, ms1000, ms2000},
		n313-r12							ENUMERATED {
												n1, n2, n3, n4, n6, n8, n10, n20},
		n314-r12							ENUMERATED {
												n1, n2, n3, n4, n5, n6, n8, n10},
		...
	}
}

-- ASN1STOP

RLF-TimersAndConstants field descriptions
n3xy
Constants are described in section 7.4. n1 corresponds with 1, n2 corresponds with 2 and so on.
t3xy
Timers are described in section 7.3. Value ms0 corresponds with 0 ms, ms50 corresponds with 50 ms and so on.

-	RN-SubframeConfig
The IE RN-SubframeConfig is used to specify the subframe configuration for an RN.
RN-SubframeConfig information element
-- ASN1START

RN-SubframeConfig-r10 ::=		SEQUENCE {
	subframeConfigPattern-r10			CHOICE {
		subframeConfigPatternFDD-r10	BIT STRING (SIZE(8)),
		subframeConfigPatternTDD-r10	INTEGER (0..31)
	}																	OPTIONAL,	-- Need ON
	rpdcch-Config-r10				SEQUENCE {
		resourceAllocationType-r10		ENUMERATED {type0, type1, type2Localized, type2Distributed,
													spare4, spare3, spare2, spare1},
		resourceBlockAssignment-r10			CHOICE {
			type01-r10							CHOICE {
				nrb6-r10							BIT STRING (SIZE(6)),
				nrb15-r10							BIT STRING (SIZE(8)),
				nrb25-r10							BIT STRING (SIZE(13)),
				nrb50-r10							BIT STRING (SIZE(17)),
				nrb75-r10							BIT STRING (SIZE(19)),
				nrb100-r10							BIT STRING (SIZE(25))
			},
			type2-r10							CHOICE {
				nrb6-r10							BIT STRING (SIZE(5)),
				nrb15-r10							BIT STRING (SIZE(7)),
				nrb25-r10							BIT STRING (SIZE(9)),
				nrb50-r10							BIT STRING (SIZE(11)),
				nrb75-r10							BIT STRING (SIZE(12)),
				nrb100-r10							BIT STRING (SIZE(13))
			},
			...
		},
		demodulationRS-r10				CHOICE {
			interleaving-r10				ENUMERATED {crs},
			noInterleaving-r10				ENUMERATED {crs, dmrs}
		},
		pdsch-Start-r10					INTEGER (1..3),
		pucch-Config-r10				CHOICE {
			tdd								CHOICE {
				channelSelectionMultiplexingBundling	SEQUENCE {
					n1PUCCH-AN-List-r10			SEQUENCE (SIZE (1..4)) OF INTEGER (0..2047)
				},
				fallbackForFormat3				SEQUENCE {
					n1PUCCH-AN-P0-r10				INTEGER (0..2047),
					n1PUCCH-AN-P1-r10				INTEGER (0..2047)		OPTIONAL	-- Need OR
				}
			},
			fdd								SEQUENCE {
				n1PUCCH-AN-P0-r10				INTEGER (0..2047),
				n1PUCCH-AN-P1-r10				INTEGER (0..2047)			OPTIONAL	-- Need OR
			}
		},
		...
	}																	OPTIONAL,	-- Need ON
	...
}

-- ASN1STOP

RN-SubframeConfig field descriptions
demodulationRS
Indicates which reference signals are used for R-PDCCH demodulation according to TS 36.216 [55, 7.4.1]. Value interleaving corresponds to cross-interleaving and value noInterleaving corresponds to no cross-interleaving according to TS 36.216 [55, 7.4.2 and 7.4.3].
n1PUCCH-AN-List
Parameter: , see TS 36.216, [55, 7.5.1]. This parameter is only applicable for TDD. Configures PUCCH HARQ-ACK resources if the RN is configured to use HARQ-ACK channel selection, HARQ-ACK multiplexing or HARQ-ACK bundling.
n1PUCCH-AN-P0, n1PUCCH-AN-P1
Parameter: , for antenna port P0 and for antenna port P1 respectively, see TS 36.216, [55, 7.5.1] for FDD and [55, 7.5.2] for TDD. 
pdsch-Start
Parameter: DL-StartSymbol, see TS 36.216 [55, Table 5.4-1].
resourceAllocationType
Represents the resource allocation used: type 0, type 1 or type 2 according to TS 36.213 [23, 7.1.6]. Value type0 corresponds to type 0, value type1 corresponds to type 1, value type2Localized corresponds to type 2 with localized virtual resource blocks and type2Distributed corresponds to type 2 with distributed virtual resource blocks.
resourceBlockAssignment
Indicates the resource block assignment bits according to TS 36.213 [23, 7.1.6]. Value type01 corresponds to type 0 and type 1, and the value type2 corresponds to type 2. Value nrb6 corresponds to a downlink system bandwidth of 6 resource blocks, value nrb15 corresponds to a downlink system bandwidth of 15 resource blocks, and so on.
subframeConfigPatternFDD
Parameter: SubframeConfigurationFDD, see TS 36.216 [55, Table 5.2-1]. Defines the DL subframe configuration for eNB-to-RN transmission, i.e. those subframes in which the eNB may indicate downlink assignments for the RN. The radio frame in which the pattern starts (i.e. the radio frame in which the first bit of the subframeConfigPatternFDD corresponds to subframe #0) occurs when SFN mod 4 = 0.
subframeConfigPatternTDD
Parameter: SubframeConfigurationTDD, see TS 36.216 [55, Table 5.2-2]. Defines the DL and UL subframe configuration for eNB-RN transmission.

-	SchedulingRequestConfig
The IE SchedulingRequestConfig is used to specify the Scheduling Request related parameters
SchedulingRequestConfig information element
-- ASN1START

SchedulingRequestConfig ::=		CHOICE {
	release								NULL,
	setup								SEQUENCE {
		sr-PUCCH-ResourceIndex				INTEGER (0..2047),
		sr-ConfigIndex						INTEGER (0..157),
		dsr-TransMax						ENUMERATED {
												n4, n8, n16, n32, n64, spare3, spare2, spare1}
	}
}

SchedulingRequestConfig-v1020 ::=	SEQUENCE {
	sr-PUCCH-ResourceIndexP1-r10		INTEGER (0..2047)			OPTIONAL		-- Need OR
}

-- ASN1STOP

SchedulingRequestConfig field descriptions
dsr-TransMax
Parameter for SR transmission in TS 36.321 [6, 5.4.4]. The value n4 corresponds to 4 transmissions, n8 corresponds to 8 transmissions and so on. EUTRAN configures the same value for all serving cells for which this field is configured.
sr-ConfigIndex
Parameter. See TS 36.213 [23,10.1]. The values 156 and 157 are not applicable for Release 8.
sr-PUCCH-ResourceIndex, sr-PUCCH-ResourceIndexP1
Parameter:  for antenna port P0 and for antenna port P1 respectively, see TS 36.213 [23, 10.1]. E-UTRAN configures sr-PUCCH-ResourceIndexP1 only if sr-PUCCHResourceIndex is configured.

-	SoundingRS-UL-Config
The IE SoundingRS-UL-Config is used to specify the uplink Sounding RS configuration for periodic and aperiodic sounding.
SoundingRS-UL-Config information element
-- ASN1START

SoundingRS-UL-ConfigCommon ::=		CHOICE {
	release								NULL,
	setup								SEQUENCE {
		srs-BandwidthConfig					ENUMERATED {bw0, bw1, bw2, bw3, bw4, bw5, bw6, bw7},
		srs-SubframeConfig					ENUMERATED {
												sc0, sc1, sc2, sc3, sc4, sc5, sc6, sc7,
												sc8, sc9, sc10, sc11, sc12, sc13, sc14, sc15},
		ackNackSRS-SimultaneousTransmission	BOOLEAN,
		srs-MaxUpPts						ENUMERATED {true}			OPTIONAL	-- Cond TDD
	}
}

SoundingRS-UL-ConfigDedicated ::=	CHOICE{
	release								NULL,
	setup								SEQUENCE {
		srs-Bandwidth						ENUMERATED {bw0, bw1, bw2, bw3},
		srs-HoppingBandwidth				ENUMERATED {hbw0, hbw1, hbw2, hbw3},
		freqDomainPosition					INTEGER (0..23),
		duration							BOOLEAN,
		srs-ConfigIndex						INTEGER (0..1023),
		transmissionComb					INTEGER (0..1),
		cyclicShift							ENUMERATED {cs0, cs1, cs2, cs3, cs4, cs5, cs6, cs7}
	}
}

SoundingRS-UL-ConfigDedicated-v1020 ::=	SEQUENCE {
	srs-AntennaPort-r10					SRS-AntennaPort
}

SoundingRS-UL-ConfigDedicated-v13x0 ::=	CHOICE{
	release								NULL,
	setup								SEQUENCE {
		transmissionComb-v13x0				INTEGER (2..3)				OPTIONAL,	-- Need OR
		cyclicShift-v13x0					ENUMERATED {cs8, cs9, cs10, cs11}	OPTIONAL,	-- Need OR
		transmissionCombNum-r13				ENUMERATED {n2, n4}		OPTIONAL	-- Need OR
	}
}

SoundingRS-UL-ConfigDedicatedUpPTsExt-r13 ::=	CHOICE{
	release								NULL,
	setup								SEQUENCE {
		srs-UpPtsAdd						ENUMERATED {sym2, sym4},
		srs-Bandwidth-r13					ENUMERATED {bw0, bw1, bw2, bw3},
		srs-HoppingBandwidth-r13			ENUMERATED {hbw0, hbw1, hbw2, hbw3},
		freqDomainPosition-r13				INTEGER (0..23),
		duration-r13						BOOLEAN,
		srs-ConfigIndex-r13					INTEGER (0..1023),
		transmissionComb-r13				INTEGER (0..3),
		cyclicShift-r13						ENUMERATED {cs0, cs1, cs2, cs3, cs4, cs5, cs6, cs7,
														cs8, cs9, cs10, cs11},
		srs-AntennaPort-r13					SRS-AntennaPort,
		transmissionCombNum-r13				ENUMERATED {n2, n4}
	}
}

SoundingRS-UL-ConfigDedicatedAperiodic-r10 ::=	CHOICE{
	release								NULL,
	setup								SEQUENCE {
		srs-ConfigIndexAp-r10				INTEGER (0..31),
		srs-ConfigApDCI-Format4-r10			SEQUENCE (SIZE (1..3)) OF SRS-ConfigAp-r10	OPTIONAL,--Need ON
		srs-ActivateAp-r10					CHOICE {
				release							NULL,
				setup							SEQUENCE {
					srs-ConfigApDCI-Format0-r10			SRS-ConfigAp-r10,
					srs-ConfigApDCI-Format1a2b2c-r10		SRS-ConfigAp-r10,
					...
				}
		}																	OPTIONAL	-- Need ON
	}
}

SoundingRS-UL-ConfigDedicatedAperiodic-v13x0 ::=	CHOICE{
	release								NULL,
	setup								SEQUENCE {
		srs-ConfigApDCI-Format4-v13x0		SEQUENCE (SIZE (1..3)) OF SRS-ConfigAp-v13x0	OPTIONAL,--Need ON
		srs-ActivateAp-v13x0				CHOICE {
				release							NULL,
				setup							SEQUENCE {
					srs-ConfigApDCI-Format0-v13x0		SRS-ConfigAp-v13x0	OPTIONAL,	-- Need ON
					srs-ConfigApDCI-Format1a2b2c-v13x0	SRS-ConfigAp-v13x0	OPTIONAL,	-- Need ON
					...
				}
		}																	OPTIONAL	-- Need ON
	}
}

SoundingRS-UL-ConfigDedicatedAperiodicUpPTsExt-r13 ::=	CHOICE{
	release								NULL,
	setup								SEQUENCE {
		srs-UpPtsAdd						ENUMERATED {sym2, sym4},
		srs-ConfigIndexAp-r13				INTEGER (0..31),
		srs-ConfigApDCI-Format4-r13			SEQUENCE (SIZE (1..3)) OF SRS-ConfigAp-r13	OPTIONAL,--Need ON
		srs-ActivateAp-r13					CHOICE {
				release							NULL,
				setup							SEQUENCE {
					srs-ConfigApDCI-Format0-r13			SRS-ConfigAp-r13,
					srs-ConfigApDCI-Format1a2b2c-r13		SRS-ConfigAp-r13,
					...
				}
		}																	OPTIONAL	-- Need ON
	}
}

SRS-ConfigAp-r10 ::= SEQUENCE {
	srs-AntennaPortAp-r10				SRS-AntennaPort,
	srs-BandwidthAp-r10					ENUMERATED {bw0, bw1, bw2, bw3},
	freqDomainPositionAp-r10			INTEGER (0..23),
	transmissionCombAp-r10				INTEGER (0..1),
	cyclicShiftAp-r10					ENUMERATED {cs0, cs1, cs2, cs3, cs4, cs5, cs6, cs7}
}

SRS-ConfigAp-v13x0 ::= SEQUENCE {
	transmissionCombAp-v13x0			INTEGER (2..3)						OPTIONAL,	-- Need OR
	cyclicShiftAp-v13x0					ENUMERATED {cs8, cs9, cs10, cs11}	OPTIONAL,	-- Need OR
	transmissionCombNum-r13				ENUMERATED {n2, n4}			OPTIONAL	-- Need OR
}

SRS-ConfigAp-r13 ::= SEQUENCE {
	srs-AntennaPortAp-r10				SRS-AntennaPort,
	srs-BandwidthAp-r10					ENUMERATED {bw0, bw1, bw2, bw3},
	freqDomainPositionAp-r10			INTEGER (0..23),
	transmissionCombAp-r10				INTEGER (0..3),
	cyclicShiftAp-r10					ENUMERATED {cs0, cs1, cs2, cs3, cs4, cs5, cs6, cs7,
											cs8, cs9, cs10, cs11},
	transmissionCombNum-r13				ENUMERATED {n2, n4}
}

SRS-AntennaPort ::=					ENUMERATED {an1, an2, an4, spare1}

-- ASN1STOP

SoundingRS-UL-Config field descriptions
ackNackSRS-SimultaneousTransmission
Parameter: Simultaneous-AN-and-SRS, see TS 36.213 [23, 8.2]. For SCells this field is not applicable and the UE shall ignore the value.
cyclicShift, cyclicShiftAp
Parameter: n_SRS for periodic and aperiodic sounding reference signal transmission respectively. See TS 36.211 [21, 5.5.3.1], where cs0 corresponds to 0 etc.
duration
Parameter: Duration for periodic sounding reference signal transmission. See TS 36.213 [21, 8.2]. FALSE corresponds to "single" and value TRUE to "indefinite".
freqDomainPosition, freqDomainPositionAp
Parameter:  for periodic and aperiodic sounding reference signal transmission respectively, see TS 36.211 [21, 5.5.3.2].
srs-AntennaPort, srs-AntennaPortAp
Indicates the number of antenna ports used for periodic and aperiodic sounding reference signal transmission respectively, see TS 36.211 [21, 5.5.3]. UE shall release srs-AntennaPort if SoundingRS-UL-ConfigDedicated is released.
srs-Bandwidth, srs-BandwidthAp
Parameter:  for periodic and aperiodic sounding reference signal transmission respectively, see TS 36.211 [21, tables 5.5.3.2-1, 5.5.3.2-2, 5.5.3.2-3 and 5.5.3.2-4].
srs-BandwidthConfig
Parameter: SRS Bandwidth Configuration. See TS 36.211, [21, table 5.5.3.2-1, 5.5.3.2-2, 5.5.3.2-3 and 5.5.3.2-4]. Actual configuration depends on UL bandwidth. bw0 corresponds to value 0, bw1 to value 1 and so on.
srs-ConfigApDCI-Format0 / srs-ConfigApDCI-Format1a2b2c / srs-ConfigApDCI-Format4
Parameters indicate the resource configurations for aperiodic sounding reference signal transmissions triggered by DCI formats 0, 1A, 2B, 2C, 4. See TS 36.213 [23, 8.2].
srs-ConfigIndex, srs-ConfigIndexAp
Parameter: ISRS for periodic and aperiodic sounding reference signal transmission respectively. See TS 36.213 [23, table 8.2-1 and table 8.2-2] for periodic and TS 36.213 [23, table 8.2-4 and table 8.2-5] for aperiodic SRS transmission.
srs-HoppingBandwidth
Parameter: SRS hopping bandwidth  for periodic sounding reference signal transmission, see TS 36.211 [21, 5.5.3.2] where hbw0 corresponds to value 0, hbw1 to value 1 and so on.
srs-MaxUpPts
Parameter: srsMaxUpPts, see TS 36.211 [21, 5.5.3.2]. If this field is present, reconfiguration of  applies for UpPts, otherwise reconfiguration does not apply.
srs-SubframeConfig
Parameter: SRS SubframeConfiguration. See TS 36.211, [21, table 5.5.3.3-1] applies for FDD whereas TS 36.211, [21, table 5.5.3.3-2] applies for TDD. sc0 corresponds to value 0, sc1 to value 1 and so on.
srs-UpPtsAdd
The field only applies for TDD. If E-UTRAN configures both soundingRS-UL-ConfigDedicatedUpPTsExt and soundingRS-UL-ConfigDedicatedAperiodicUpPTsExt it shall set srs-UpPtsAdd to in both fields to the same value
transmissionComb, transmissionCombAp
Parameter:  for periodic and aperiodic sounding reference signal transmission respectively, see TS 36.211 [21, 5.5.3.2].

Conditional presence
Explanation
TDD
This field is optional present for TDD, need OR; it is not present for FDD and the UE shall delete any existing value for this field.

-	SPS-Config
The IE SPS-Config is used to specify the semi-persistent scheduling configuration.
SPS-Config information element
-- ASN1START

SPS-Config ::=	SEQUENCE {
	semiPersistSchedC-RNTI			C-RNTI					OPTIONAL,			-- Need OR
	sps-ConfigDL					SPS-ConfigDL			OPTIONAL,			-- Need ON
	sps-ConfigUL					SPS-ConfigUL			OPTIONAL			-- Need ON
}

SPS-ConfigDL ::=	CHOICE{
	release							NULL,
	setup							SEQUENCE {
		semiPersistSchedIntervalDL			ENUMERATED {
												sf10, sf20, sf32, sf40, sf64, sf80,
												sf128, sf160, sf320, sf640, spare6,
												spare5, spare4, spare3, spare2,
												spare1},
		numberOfConfSPS-Processes			INTEGER (1..8),
		n1PUCCH-AN-PersistentList			N1PUCCH-AN-PersistentList,
		...,
		[[	twoAntennaPortActivated-r10		CHOICE {
				release							NULL,
				setup							SEQUENCE {
					n1PUCCH-AN-PersistentListP1-r10	N1PUCCH-AN-PersistentList
				}
			}																OPTIONAL	-- Need ON
		]]
	}
}

SPS-ConfigUL ::=	CHOICE {
	release							NULL,
	setup							SEQUENCE {
		semiPersistSchedIntervalUL			ENUMERATED {
												sf10, sf20, sf32, sf40, sf64, sf80,
												sf128, sf160, sf320, sf640, spare6,
												spare5, spare4, spare3, spare2,
												spare1},
		implicitReleaseAfter				ENUMERATED {e2, e3, e4, e8},
		p0-Persistent						SEQUENCE {
			p0-NominalPUSCH-Persistent			INTEGER (-126..24),
			p0-UE-PUSCH-Persistent				INTEGER (-8..7)
		}		OPTIONAL,												-- Need OP
		twoIntervalsConfig					ENUMERATED {true}			OPTIONAL,	-- Cond TDD
		...,
		[[	p0-PersistentSubframeSet2-r12		CHOICE {
				release								NULL,
				setup								SEQUENCE {
					p0-NominalPUSCH-PersistentSubframeSet2-r12			INTEGER (-126..24),
					p0-UE-PUSCH-PersistentSubframeSet2-r12				INTEGER (-8..7)
				}
			} 															OPTIONAL	-- Need ON
		]]
	}
}

N1PUCCH-AN-PersistentList ::=		SEQUENCE (SIZE (1..4)) OF INTEGER (0..2047)

-- ASN1STOP

SPS-Config field descriptions
implicitReleaseAfter
Number of empty transmissions before implicit release, see TS 36.321 [6, 5.10.2]. Value e2 corresponds to 2 transmissions, e3 corresponds to 3 transmissions and so on.
n1PUCCH-AN-PersistentList , n1PUCCH-AN-PersistentListP1
List of parameter:  for antenna port P0 and for antenna port P1 respectively, see TS 36.213 [23, 10.1]. Field n1-PUCCH-AN-PersistentListP1 is applicable only if the twoAntennaPortActivatedPUCCH-Format1a1b in PUCCH-ConfigDedicated-v1020 is set to true. Otherwise the field is not configured.
numberOfConfSPS-Processes
The number of configured HARQ processes for Semi-Persistent Scheduling, see TS 36.321 [6].
p0-NominalPUSCH-Persistent
Parameter: . See TS 36.213 [23, 5.1.1.1], unit dBm step 1. This field is applicable for persistent scheduling, only. If choice setup is used and p0-Persistent is absent, apply the value of p0-NominalPUSCH for p0-NominalPUSCH-Persistent. If uplink power control subframe sets are configured by tpc-SubframeSet, this field applies for uplink power control subframe set 1.
p0-NominalPUSCH-PersistentSubframeSet2
Parameter: . See TS 36.213 [23, 5.1.1.1], unit dBm step 1. This field is applicable for persistent scheduling, only. If p0-PersistentSubframeSet2-r12 is not configured, apply the value of p0-NominalPUSCH-SubframeSet2-r12 for p0-NominalPUSCH-PersistentSubframeSet2. E-UTRAN configures this field only if uplink power control subframe sets are configured by tpc-SubframeSet, in which case this field applies for uplink power control subframe set 2.
p0-UE-PUSCH-Persistent
Parameter: . See TS 36.213 [23, 5.1.1.1], unit dB. This field is applicable for persistent scheduling, only. If choice setup is used and p0-Persistent is absent, apply the value of p0-UE-PUSCH for p0-UE-PUSCH-Persistent. If uplink power control subframe sets are configured by tpc-SubframeSet, this field applies for uplink power control subframe set 1.
p0-UE-PUSCH-PersistentSubframeSet2
Parameter: . See TS 36.213 [23, 5.1.1.1], unit dB. This field is applicable for persistent scheduling, only. If p0-PersistentSubframeSet2-r12 is not configured, apply the value of p0-UE-PUSCH-SubframeSet2 for p0-UE-PUSCH-PersistentSubframeSet2. E-UTRAN configures this field only if uplink power control subframe sets are configured by tpc-SubframeSet, in which case this field applies for uplink power control subframe set 2.
semiPersistSchedC-RNTI
Semi-persistent Scheduling C-RNTI, see TS 36.321 [6].
semiPersistSchedIntervalDL
Semi-persistent scheduling interval in downlink, see TS 36.321 [6]. Value in number of sub-frames. Value sf10 corresponds to 10 sub-frames, sf20 corresponds to 20 sub-frames and so on. For TDD, the UE shall round this parameter down to the nearest integer (of 10 sub-frames), e.g. sf10 corresponds to 10 sub-frames, sf32 corresponds to 30 sub-frames, sf128 corresponds to 120 sub-frames.
semiPersistSchedIntervalUL
Semi-persistent scheduling interval in uplink, see TS 36.321 [6]. Value in number of sub-frames. Value sf10 corresponds to 10 sub-frames, sf20 corresponds to 20 sub-frames and so on. For TDD, the UE shall round this parameter down to the nearest integer (of 10 sub-frames), e.g. sf10 corresponds to 10 sub-frames, sf32 corresponds to 30 sub-frames, sf128 corresponds to 120 sub-frames.
twoIntervalsConfig
Trigger of two-intervals-Semi-Persistent Scheduling in uplink. See TS 36.321 [6, 5.10]. If this field is present, two-intervals-SPS is enabled for uplink. Otherwise, two-intervals-SPS is disabled.

Conditional presence
Explanation
TDD
This field is optional present for TDD, need OR; it is not present for FDD and the UE shall delete any existing value for this field.

-	TDD-Config
The IE TDD-Config is used to specify the TDD specific physical channel configuration.
TDD-Config information element
-- ASN1START

TDD-Config ::=						SEQUENCE {
	subframeAssignment					ENUMERATED {
											sa0, sa1, sa2, sa3, sa4, sa5, sa6},
	specialSubframePatterns				ENUMERATED {
											ssp0, ssp1, ssp2, ssp3, ssp4,ssp5, ssp6, ssp7,
											ssp8}
}

TDD-Config-v1130 ::=				SEQUENCE {
	specialSubframePatterns-v1130		ENUMERATED {ssp7,ssp9}
}

TDD-ConfigSL-r12 ::=		SEQUENCE {
	subframeAssignmentSL-r12				ENUMERATED {
											none, sa0, sa1, sa2, sa3, sa4, sa5, sa6}
}

-- ASN1STOP

TDD-Config field descriptions
specialSubframePatterns
Indicates Configuration as in TS 36.211 [21, table 4.2-1] where ssp0 points to Configuration 0, ssp1 to Configuration 1 etc. Value ssp7 points to Configuration 7 for extended cyclic prefix and value ssp9 points to Configuration 9 for normal cyclic prefix. E-UTRAN signals ssp7 only when setting specialSubframePatterns (without suffix i.e. the version defined in REL-8) to ssp4. E-UTRAN signals value ssp9 only when setting specialSubframePatterns (without suffix) to ssp5. If specialSubframePatterns-v1130 is present, the UE shall ignore specialSubframePatterns (without suffix).
subframeAssignment
Indicates DL/UL subframe configuration where sa0 points to Configuration 0, sa1 to Configuration 1 etc. as specified in TS 36.211 [21, table 4.2-2]. E-UTRAN configures the same value for serving cells residing on same frequency band.
subframeAssignmentSL
Indicates UL/ DL subframe configuration where sa0 points to Configuration 0, sa1 to Configuration 1 etc. as specified in TS 36.211 [21, table 4.2-2]. The value none means that no TDD specific physical channel configuration is applicable (i.e. the carrier on which MasterInformationBlock-SL is transmitted is an FDD UL carrier).

-	TimeAlignmentTimer
The IE TimeAlignmentTimer is used to control how long the UE considers the serving cells belonging to the associated TAG to be uplink time aligned. Corresponds to the Timer for time alignment in TS 36.321 [6]. Value in number of sub-frames. Value sf500 corresponds to 500 sub-frames, sf750 corresponds to 750 sub-frames and so on.
TimeAlignmentTimer information element
-- ASN1START

TimeAlignmentTimer ::=					ENUMERATED {
												sf500, sf750, sf1280, sf1920, sf2560, sf5120,
												sf10240, infinity}
-- ASN1STOP

-	TPC-PDCCH-Config
The IE TPC-PDCCH-Config is used to specify the RNTIs and indexes for PUCCH and PUSCH power control according to TS 36.212 [22]. The power control function can either be setup or released with the IE.
TPC-PDCCH-Config information element
-- ASN1START

TPC-PDCCH-Config ::=					CHOICE {
	release								NULL,
	setup								SEQUENCE {
		tpc-RNTI							BIT STRING (SIZE (16)),
		tpc-Index							TPC-Index
	}
}

TPC-PDCCH-ConfigSCell ::=					CHOICE {
	release								NULL,
	setup								SEQUENCE {
		tpc-Index-PUCCH-SCell-r13		TPC-Index
	}
}

TPC-Index ::=							CHOICE {
	indexOfFormat3							INTEGER (1..15),
	indexOfFormat3A							INTEGER (1..31)
}

-- ASN1STOP

TPC-PDCCH-Config field descriptions
indexOfFormat3
Index of N when DCI format 3 is used. See TS 36.212 [22, 5.3.3.1.6].
IndexOfFormat3A
Index of M when DCI format 3A is used. See TS 36.212 [22, 5.3.3.1.7].
tpc-Index
Index of N or M, see TS 36.212 [22, 5.3.3.1.6 and 5.3.3.1.7], where N or M is dependent on the used DCI format (i.e. format 3 or 3a).
tpc-Index-PUCCH-SCell
Index of N or M, see TS 36.212 [22, x.y], where N or M is dependent on the used DCI format (i.e. format 3 or 3a).
tpc-RNTI
RNTI for power control using DCI format 3/3A, see TS 36.212 [22].

-	UplinkPowerControl
The IE UplinkPowerControlCommon and IE UplinkPowerControlDedicated are used to specify parameters for uplink power control in the system information and in the dedicated signalling, respectively.
UplinkPowerControl information elements
-- ASN1START

UplinkPowerControlCommon ::=		SEQUENCE {
	p0-NominalPUSCH						INTEGER (-126..24),
	alpha								Alpha-r12,
	p0-NominalPUCCH						INTEGER (-127..-96),
	deltaFList-PUCCH					DeltaFList-PUCCH,
	deltaPreambleMsg3					INTEGER (-1..6)
}

UplinkPowerControlCommon-v1020 ::=	SEQUENCE {
	deltaF-PUCCH-Format3-r10				ENUMERATED {deltaF-1, deltaF0, deltaF1, deltaF2,
														deltaF3, deltaF4, deltaF5, deltaF6},
	deltaF-PUCCH-Format1bCS-r10				ENUMERATED {deltaF1, deltaF2, spare2, spare1}
}

UplinkPowerControlCommon-v13xy ::=	SEQUENCE {
	deltaF-PUCCH-Format4				ENUMERATED {deltaFX, deltaFX1, deltaFX2,deltaFX3, deltaFX4, deltaFX5, deltaFX6, deltaFX7}		OPTIONAL,		-- Need OR
	deltaF-PUCCH-Format5				ENUMERATED { deltaFX, deltaFX1, deltaFX2, deltaFX3, deltaFX4, deltaFX5, deltaFX6, deltaFX7}		OPTIONAL			-- Need OR
}

UplinkPowerControlCommonPSCell-r12 ::=		SEQUENCE {
-- For uplink power control the additional/ missing fields are signalled (compared to SCell)
	deltaF-PUCCH-Format3-r12				ENUMERATED {deltaF-1, deltaF0, deltaF1, deltaF2,
														deltaF3, deltaF4, deltaF5, deltaF6},
	deltaF-PUCCH-Format1bCS-r12				ENUMERATED {deltaF1, deltaF2, spare2, spare1},
	p0-NominalPUCCH-r12						INTEGER (-127..-96),
	deltaFList-PUCCH-r12					DeltaFList-PUCCH
}

UplinkPowerControlCommonPSCell-v13xy ::=		SEQUENCE {
-- For uplink power control the additional/ missing fields are signalled (compared to SCell)
	deltaF-PUCCH-Format4				ENUMERATED {deltaFX, deltaFX1, deltaFX2,deltaFX3, deltaFX4, deltaFX5, deltaFX6, deltaFX7}		OPTIONAL,		-- Need OR
	deltaF-PUCCH-Format5				ENUMERATED { deltaFX, deltaFX1, deltaFX2,deltaFX3, deltaFX4, deltaFX5, deltaFX6, deltaFX7}		OPTIONAL		-- Need OR
}

UplinkPowerControlCommonSCell-r10 ::=	SEQUENCE {
	p0-NominalPUSCH-r10					INTEGER (-126..24),
	alpha-r10							Alpha-r12
}

UplinkPowerControlCommonSCell-v1130 ::=	SEQUENCE {
	deltaPreambleMsg3-r11				INTEGER (-1..6)
}

UplinkPowerControlDedicated ::=		SEQUENCE {
	p0-UE-PUSCH							INTEGER (-8..7),
	deltaMCS-Enabled					ENUMERATED {en0, en1},
	accumulationEnabled					BOOLEAN,
	p0-UE-PUCCH							INTEGER (-8..7),
	pSRS-Offset							INTEGER (0..15),
	filterCoefficient					FilterCoefficient					DEFAULT fc4
}

UplinkPowerControlDedicated-v1020 ::= SEQUENCE {
	deltaTxD-OffsetListPUCCH-r10		DeltaTxD-OffsetListPUCCH-r10	OPTIONAL,		-- Need OR
	pSRS-OffsetAp-r10					INTEGER (0..15)					OPTIONAL		-- Need OR
}

UplinkPowerControlDedicated-v1130 ::=		SEQUENCE {
	pSRS-Offset-v1130						INTEGER (16..31)			OPTIONAL,		-- Need OR
	pSRS-OffsetAp-v1130						INTEGER (16..31)			OPTIONAL,		-- Need OR
	deltaTxD-OffsetListPUCCH-v1130			DeltaTxD-OffsetListPUCCH-v1130	OPTIONAL	-- Need OR
}

UplinkPowerControlDedicated-v1250 ::=	SEQUENCE {
	set2PowerControlParameter		CHOICE {
		release							NULL,
		setup							SEQUENCE {
			tpc-SubframeSet-r12					BIT STRING (SIZE(10)),
			p0-NominalPUSCH-SubframeSet2-r12		INTEGER (-126..24),
			alpha-SubframeSet2-r12				Alpha-r12,
			p0-UE-PUSCH-SubframeSet2-r12			INTEGER (-8..7)
		}
	}
}

UplinkPowerControlDedicatedSCell-r10 ::=		SEQUENCE {
	p0-UE-PUSCH-r10						INTEGER (-8..7),
	deltaMCS-Enabled-r10					ENUMERATED {en0, en1},
	accumulationEnabled-r10				BOOLEAN,
	pSRS-Offset-r10						INTEGER (0..15),
	pSRS-OffsetAp-r10					INTEGER (0..15) 					OPTIONAL,	-- Need OR
	filterCoefficient-r10				FilterCoefficient					DEFAULT fc4,
	pathlossReferenceLinking-r10		ENUMERATED {pCell, sCell}
}

Alpha-r12 ::=						ENUMERATED {al0, al04, al05, al06, al07, al08, al09, al1}

DeltaFList-PUCCH ::=				SEQUENCE {
	deltaF-PUCCH-Format1				ENUMERATED {deltaF-2, deltaF0, deltaF2},
	deltaF-PUCCH-Format1b				ENUMERATED {deltaF1, deltaF3, deltaF5},
	deltaF-PUCCH-Format2				ENUMERATED {deltaF-2, deltaF0, deltaF1, deltaF2},
	deltaF-PUCCH-Format2a				ENUMERATED {deltaF-2, deltaF0, deltaF2},
	deltaF-PUCCH-Format2b				ENUMERATED {deltaF-2, deltaF0, deltaF2}
}

DeltaTxD-OffsetListPUCCH-r10 ::=	SEQUENCE {
	deltaTxD-OffsetPUCCH-Format1-r10		ENUMERATED {dB0, dB-2},
	deltaTxD-OffsetPUCCH-Format1a1b-r10		ENUMERATED {dB0, dB-2},
	deltaTxD-OffsetPUCCH-Format22a2b-r10	ENUMERATED {dB0, dB-2},
	deltaTxD-OffsetPUCCH-Format3-r10		ENUMERATED {dB0, dB-2},
	...

}

DeltaTxD-OffsetListPUCCH-v1130 ::=	SEQUENCE {
	deltaTxD-OffsetPUCCH-Format1bCS-r11		ENUMERATED {dB0, dB-1}
}
-- ASN1STOP

UplinkPowerControl field descriptions
accumulationEnabled
Parameter: Accumulation-enabled, see TS 36.213 [23, 5.1.1.1]. TRUE corresponds to "enabled" whereas FALSE corresponds to "disabled".
alpha
Parameter: ? See TS 36.213 [23, 5.1.1.1] where al0 corresponds to 0, al04 corresponds to value 0.4, al05 to 0.5, al06 to 0.6, al07 to 0.7, al08 to 0.8, al09 to 0.9 and al1 corresponds to 1. This field applies for uplink power control subframe set 1 if uplink power control subframe sets are configured by tpc-SubframeSet.
alpha-SubframeSet2
Parameter: ?. See TS 36.213 [23, 5.1.1.1] where al0 corresponds to 0, al04 corresponds to value 0.4, al05 to 0.5, al06 to 0.6, al07 to 0.7, al08 to 0.8, al09 to 0.9 and al1 corresponds to 1. This field applies for uplink power control subframe set 2 if uplink power control subframe sets are configured by tpc-SubframeSet.
deltaF-PUCCH-FormatX
Parameter:  for the PUCCH formats 1, 1b, 2, 2a, 2b, 3, 4, 5 and 1b with channel selection. See TS 36.213 [23, 5.1.2] where deltaF-2 corresponds to -2 dB, deltaF0 corresponds to 0 dB and so on.
deltaMCS-Enabled
Parameter: Ks See TS 36.213 [23, 5.1.1.1]. en0 corresponds to value 0 corresponding to state "disabled". en1 corresponds to value 1.25 corresponding to "enabled".
deltaPreambleMsg3
Parameter:  see TS 36.213 [23, 5.1.1.1]. Actual value = IE value * 2 [dB].
deltaTxD-OffsetPUCCH-FormatX
Parameter:  for the PUCCH formats 1, 1a/1b, 1b with channel selection, 2/2a/2b and 3 when two antenna ports are configured for PUCCH transmission. See TS 36.213 [23, 5.1.2.1] where dB0 corresponds to 0 dB, dB-1 corresponds to -1 dB, dB-2 corresponds to -2 dB. EUTRAN configures the field deltaTxD-OffsetPUCCH-Format1bCS-r11 for the PCell and/or the PSCell only.
filterCoefficient
Specifies the filtering coefficient for RSRP measurements used to calculate path loss, as specified in TS 36.213 [23, 5.1.1.1]. The same filtering mechanism applies as for quantityConfig described in 5.5.3.2.
p0-NominalPUCCH
Parameter:  See TS 36.213 [23, 5.1.2.1], unit dBm.
p0-NominalPUSCH
Parameter:  See TS 36.213 [23, 5.1.1.1], unit dBm. This field is applicable for non-persistent scheduling only. This field applies for uplink power control subframe set 1 if uplink power control subframe sets are configured by tpc-SubframeSet.
p0-NominalPUSCH-SubframeSet2
Parameter: . See TS 36.213 [23, 5.1.1.1], unit dBm. This field is applicable for non-persistent scheduling only. This field applies for uplink power control subframe set 2 if uplink power control subframe sets are configured by tpc-SubframeSet.
p0-UE-PUCCH
Parameter:  See TS 36.213 [23, 5.1.2.1]. Unit dB
p0-UE-PUSCH
Parameter:  See TS 36.213 [23, 5.1.1.1], unit dB. This field is applicable for non-persistent scheduling, only. This field applies for uplink power control subframe set 1 if uplink power control subframe sets are configured by tpc-SubframeSet.
p0-UE-PUSCH-SubframeSet2
Parameter:  See TS 36.213 [23, 5.1.1.1], unit dB. This field is applicable for non-persistent scheduling, only. This field applies for uplink power control subframe set 2 if uplink power control subframe sets are configured by tpc-SubframeSet.
pathlossReferenceLinking
Indicates whether the UE shall apply as pathloss reference either the downlink of the PCell or of the SCell that corresponds with this uplink (i.e. according to the cellIdentification within the field sCellToAddMod). For SCells part of an STAG E-UTRAN sets the value to sCell.
pSRS-Offset, pSRS-OffsetAp
Parameter: PSRS_OFFSET for periodic and aperiodic sounding reference signal transmission repectively. See TS 36.213 [23, 5.1.3.1]. For Ks=1.25, the actual parameter value is pSRS-Offset value - 3. For Ks=0, the actual parameter value is -10.5 + 1.5*pSRS-Offset value.
If pSRS-Offset-v1130 is included, the UE ignores pSRS-Offset (i.e., without suffix). Likewise, if pSRS-OffsetAp-v1130 is included, the UE ignores pSRS-OffsetAp-r10. For Ks=0, E-UTRAN does not set values larger than 26.
tpc-SubframeSet
Indicates the uplink subframes (including UpPTS in special subframes) of the uplink power control subframe sets. Value 0 means the subframe belongs to uplink power control subframe set 1, and value 1 means the subframe belongs to uplink power control subframe set 2.

6.3.3	Security control information elements
-	NextHopChainingCount
The IE NextHopChainingCount is used to update the KeNB key and corresponds to parameter NCC: See TS 33.401 [32, 7.2.8.4].
NextHopChainingCount information element
-- ASN1START

NextHopChainingCount ::=					INTEGER (0..7)

-- ASN1STOP

-	SecurityAlgorithmConfig
The IE SecurityAlgorithmConfig is used to configure AS integrity protection algorithm (SRBs) and AS ciphering algorithm (SRBs and DRBs). For RNs, the IE SecurityAlgorithmConfig is also used to configure AS integrity protection algorithm for DRBs between the RN and the E-UTRAN.
SecurityAlgorithmConfig information element
-- ASN1START

SecurityAlgorithmConfig ::=			SEQUENCE {
	cipheringAlgorithm					CipheringAlgorithm-r12,
	integrityProtAlgorithm				ENUMERATED {
											eia0-v920, eia1, eia2, eia3-v1130, spare4, spare3,
											spare2, spare1, ...}
}

CipheringAlgorithm-r12 ::=				ENUMERATED {
											eea0, eea1, eea2, eea3-v1130, spare4, spare3,
											spare2, spare1, ...}

-- ASN1STOP

SecurityAlgorithmConfig field descriptions
cipheringAlgorithm
Indicates the ciphering algorithm to be used for SRBs and DRBs, as specified in TS 33.401 [32, 5.1.3.2].
integrityProtAlgorithm
Indicates the integrity protection algorithm to be used for SRBs, as specified in TS 33.401 [32, 5.1.4.2]. For RNs, also indicates the integrity protection algorithm to be used for integrity protection-enabled DRB(s).

-	ShortMAC-I
The IE ShortMAC-I is used to identify and verify the UE at RRC connection re-establishment. The 16 least significant bits of the MAC-I calculated using the security configuration of the source PCell, as specified in 5.3.7.4.
ShortMAC-I information element
-- ASN1START

ShortMAC-I ::=						BIT STRING (SIZE (16))

-- ASN1STOP

6.3.4	Mobility control information elements
-	AdditionalSpectrumEmission
AdditionalSpectrumEmission information element
-- ASN1START

AdditionalSpectrumEmission ::=		INTEGER (1..32)

-- ASN1STOP

-	ARFCN-ValueCDMA2000
The IE ARFCN-ValueCDMA2000 used to indicate the CDMA2000 carrier frequency within a CDMA2000 band, see C.S0002 [12].
ARFCN-ValueCDMA2000 information element
-- ASN1START

ARFCN-ValueCDMA2000 ::=			INTEGER (0..2047)

-- ASN1STOP

-	ARFCN-ValueEUTRA
The IE ARFCN-ValueEUTRA is used to indicate the ARFCN applicable for a downlink, uplink or bi-directional (TDD) E-UTRA carrier frequency, as defined in TS 36.101 [42]. If an extension is signalled using the extended value range (as defined by IE ARFCN-ValueEUTRA-v9e0), the UE shall only consider this extension (and hence ignore the corresponding original field, using the value range as defined by IE ARFCN-ValueEUTRA i.e. without suffix, if signalled). In dedicated signalling, E-UTRAN only provides an EARFCN corresponding to an E-UTRA band supported by the UE.
ARFCN-ValueEUTRA information element
-- ASN1START

ARFCN-ValueEUTRA ::=				INTEGER (0..maxEARFCN)

ARFCN-ValueEUTRA-v9e0 ::=			INTEGER (maxEARFCN-Plus1..maxEARFCN2)

ARFCN-ValueEUTRA-r9 ::=				INTEGER (0..maxEARFCN2)

-- ASN1STOP

NOTE:	For fields using the original value range, as defined by IE ARFCN-ValueEUTRA i.e. without suffix, value maxEARFCN indicates that the E-UTRA carrier frequency is indicated by means of an extension. In such a case, UEs not supporting the extension consider the field to be set to a not supported value.

-	ARFCN-ValueGERAN
The IE ARFCN-ValueGERAN is used to specify the ARFCN value applicable for a GERAN BCCH carrier frequency, see TS 45.005 [20].
ARFCN-ValueGERAN information element
-- ASN1START

ARFCN-ValueGERAN ::=			INTEGER (0..1023)

-- ASN1STOP

-	ARFCN-ValueUTRA
The IE ARFCN-ValueUTRA is used to indicate the ARFCN applicable for a downlink (Nd, FDD) or bi-directional (Nt, TDD) UTRA carrier frequency, as defined in TS 25.331 [19].
ARFCN-ValueUTRA information element
-- ASN1START

ARFCN-ValueUTRA ::=					INTEGER (0..16383)

-- ASN1STOP

-	BandclassCDMA2000
The IE BandclassCDMA2000 is used to define the CDMA2000 band in which the CDMA2000 carrier frequency can be found, as defined in C.S0057 [24, table 1.5-1].
BandclassCDMA2000 information element
-- ASN1START

BandclassCDMA2000 ::=					ENUMERATED {
											bc0, bc1, bc2, bc3, bc4, bc5, bc6, bc7, bc8,
											bc9, bc10, bc11, bc12, bc13, bc14, bc15, bc16,
											bc17, bc18-v9a0, bc19-v9a0, bc20-v9a0, bc21-v9a0,
											spare10, spare9, spare8, spare7, spare6, spare5, spare4,
											spare3, spare2, spare1, ...}

-- ASN1STOP

-	BandIndicatorGERAN
The IE BandIndicatorGERAN indicates how to interpret an associated GERAN carrier ARFCN, see TS 45.005 [20]. More specifically, the IE indicates the GERAN frequency band in case the ARFCN value can concern either a DCS 1800 or a PCS 1900 carrier frequency. For ARFCN values not associated with one of these bands, the indicator has no meaning.
BandIndicatorGERAN information element
-- ASN1START

BandIndicatorGERAN ::=			ENUMERATED {dcs1800, pcs1900}

-- ASN1STOP

-	CarrierFreqCDMA2000
The IE CarrierFreqCDMA2000 used to provide the CDMA2000 carrier information.
CarrierFreqCDMA2000 information element
-- ASN1START

CarrierFreqCDMA2000 ::=			SEQUENCE {
	bandClass							BandclassCDMA2000,
	arfcn							ARFCN-ValueCDMA2000
}

-- ASN1STOP

-	CarrierFreqGERAN
The IE CarrierFreqGERAN is used to provide an unambiguous carrier frequency description of a GERAN cell.
CarrierFreqGERAN information element
-- ASN1START

CarrierFreqGERAN ::=			SEQUENCE {
	arfcn							ARFCN-ValueGERAN,
	bandIndicator					BandIndicatorGERAN
}

-- ASN1STOP

CarrierFreqGERAN field descriptions
arfcn
GERAN ARFCN of BCCH carrier.
bandIndicator
Indicates how to interpret the ARFCN of the BCCH carrier.

-	CarrierFreqsGERAN
The IE CarrierFreqListGERAN is used to provide one or more GERAN ARFCN values, as defined in TS 44.005 [43], which represents a list of GERAN BCCH carrier frequencies.
CarrierFreqsGERAN information element
-- ASN1START

CarrierFreqsGERAN ::=			SEQUENCE {
	startingARFCN						ARFCN-ValueGERAN,
	bandIndicator						BandIndicatorGERAN,
	followingARFCNs						CHOICE {
		explicitListOfARFCNs				ExplicitListOfARFCNs,
		equallySpacedARFCNs					SEQUENCE {
			arfcn-Spacing						INTEGER (1..8),
			numberOfFollowingARFCNs				INTEGER (0..31)
		},
		variableBitMapOfARFCNs				OCTET STRING (SIZE (1..16))
	}
}

ExplicitListOfARFCNs ::=			SEQUENCE (SIZE (0..31)) OF ARFCN-ValueGERAN

-- ASN1STOP

CarrierFreqsGERAN field descriptions
arfcn-Spacing
Space, d, between a set of equally spaced ARFCN values.
bandIndicator
Indicates how to interpret the ARFCN of the BCCH carrier.
explicitListOfARFCNs
The remaining ARFCN values in the set are explicitly listed one by one.
followingARFCNs
Field containing a representation of the remaining ARFCN values in the set.
numberOfFollowingARFCNs
The number, n, of the remaining equally spaced ARFCN values in the set. The complete set of (n+1) ARFCN values is defined as: {s, ((s + d) mod 1024), ((s + 2*d) mod 1024) ... ((s + n*d) mod 1024)}.
startingARFCN
The first ARFCN value, s, in the set.
variableBitMapOfARFCNs
Bitmap field representing the remaining ARFCN values in the set. The leading bit of the first octet in the bitmap corresponds to the ARFCN = ((s + 1) mod 1024), the next bit to the ARFCN = ((s + 2) mod 1024), and so on. If the bitmap consist of N octets, the trailing bit of octet N corresponds to ARFCN = ((s + 8*N) mod 1024). The complete set of ARFCN values consists of ARFCN = s and the ARFCN values, where the corresponding bit in the bitmap is set to "1".

-	CarrierFreqListMBMS
The IE CarrierFreqListMBMS is used to indicate the E-UTRA ARFCN values of the one or more MBMS frequencies the UE is interested to receive.
CarrierFreqListMBMS information element
-- ASN1START

CarrierFreqListMBMS-r11 ::=		SEQUENCE (SIZE (1..maxFreqMBMS-r11)) OF ARFCN-ValueEUTRA-r9

-- ASN1STOP

-	CDMA2000-Type
The IE CDMA2000-Type is used to describe the type of CDMA2000 network.
CDMA2000-Type information element
-- ASN1START

CDMA2000-Type ::=					ENUMERATED {type1XRTT, typeHRPD}

-- ASN1STOP

-	CellIdentity
The IE CellIdentity is used to unambiguously identify a cell within a PLMN.
CellIdentity information element
-- ASN1START

CellIdentity ::=					BIT STRING (SIZE (28))

-- ASN1STOP

-	CellIndexList
The IE CellIndexList concerns a list of cell indices, which may be used for different purposes.
CellIndexList information element
-- ASN1START

CellIndexList ::=						SEQUENCE (SIZE (1..maxCellMeas)) OF CellIndex

CellIndex ::=							INTEGER (1..maxCellMeas)

-- ASN1STOP

-	CellReselectionPriority
The IE CellReselectionPriority concerns the absolute priority of the concerned carrier frequency/ set of frequencies (GERAN)/ bandclass (CDMA2000), as used by the cell reselection procedure. Corresponds with parameter "priority" in TS 36.304 [4]. Value 0 means: lowest priority. The UE behaviour for the case the field is absent, if applicable, is specified in TS 36.304 [4].
CellReselectionPriority information element
-- ASN1START

CellReselectionPriority ::=				INTEGER (0..7)

-- ASN1STOP

-	CellReselectionSubPriority
The IE CellReselectionSubPriority indicates an input parameter to derive the ultimate priority of the concerned carrier frequency for E-UTRAN to be used in Cell Reselection process, as defined in TS 36.304 [4]. The value of CellReselectionSubPriority is added to the value of cellReselectionPriority. Value oDot2 corresponds to 0.2, oDot4 corresponds to 0.4 and so on.
CellReselectionSubPriority information element
-- ASN1START

CellReselectionSubPriority-r13 ::=			ENUMERATED {oDot2, oDot4, oDot6, oDot8}

-- ASN1STOP

-	CSFB-RegistrationParam1XRTT
The IE CSFB-RegistrationParam1XRTT is used to indicate whether or not the UE shall perform a CDMA2000 1xRTT pre-registration if the UE does not have a valid / current pre-registration.
-- ASN1START

CSFB-RegistrationParam1XRTT ::=		SEQUENCE {
	sid									BIT STRING (SIZE (15)),
	nid									BIT STRING (SIZE (16)),
	multipleSID							BOOLEAN,
	multipleNID							BOOLEAN,
	homeReg								BOOLEAN,
	foreignSIDReg						BOOLEAN,
	foreignNIDReg						BOOLEAN,
	parameterReg						BOOLEAN,
	powerUpReg							BOOLEAN,
	registrationPeriod					BIT STRING (SIZE (7)),
	registrationZone					BIT STRING (SIZE (12)),
	totalZone							BIT STRING (SIZE (3)),
	zoneTimer							BIT STRING (SIZE (3))
}

CSFB-RegistrationParam1XRTT-v920 ::=	SEQUENCE {
	powerDownReg-r9						ENUMERATED {true}
}

-- ASN1STOP


CSFB-RegistrationParam1XRTT field descriptions
foreignNIDReg
The CDMA2000 1xRTT NID roamer registration indicator.
foreignSIDReg
The CDMA2000 1xRTT SID roamer registration indicator.
homeReg
The CDMA2000 1xRTT Home registration indicator.
multipleNID
The CDMA2000 1xRTT Multiple NID storage indicator.
multipleSID
The CDMA2000 1xRTT Multiple SID storage indicator.
nid
Used along with the sid as a pair to control when the UE should Register or Re-Register with the CDMA2000 1xRTT network.
parameterReg
The CDMA2000 1xRTT Parameter-change registration indicator.
powerDownReg
The CDMA2000 1xRTT Power-down registration indicator. If set to TRUE, the UE that has a valid / current CDMA2000 1xRTT pre-registration will perform a CDMA2000 1xRTT power down registration when it is switched off.
powerUpReg
The CDMA2000 1xRTT Power-up registration indicator.
registrationPeriod
The CDMA2000 1xRTT Registration period.
registrationZone
The CDMA2000 1xRTT Registration zone.
sid
Used along with the nid as a pair to control when the UE should Register or Re-Register with the CDMA2000 1xRTT network.
totalZone
The CDMA2000 1xRTT Number of registration zones to be retained.
zoneTimer
The CDMA2000 1xRTT Zone timer length.

-	CellGlobalIdEUTRA
The IE CellGlobalIdEUTRA specifies the Evolved Cell Global Identifier (ECGI), the globally unique identity of a cell in E-UTRA.
CellGlobalIdEUTRA information element
-- ASN1START

CellGlobalIdEUTRA ::=					SEQUENCE {
	plmn-Identity							PLMN-Identity,
	cellIdentity							CellIdentity
}

-- ASN1STOP

CellGlobalIdEUTRA field descriptions
cellIdentity
Identity of the cell within the context of the PLMN.
plmn-Identity
Identifies the PLMN of the cell as given by the first PLMN entry in the plmn-IdentityList in SystemInformationBlockType1.

-	CellGlobalIdUTRA
The IE CellGlobalIdUTRA specifies the global UTRAN Cell Identifier, the globally unique identity of a cell in UTRA.
CellGlobalIdUTRA information element
-- ASN1START

CellGlobalIdUTRA ::=					SEQUENCE {
	plmn-Identity							PLMN-Identity,
	cellIdentity							BIT STRING (SIZE (28))
}

-- ASN1STOP

CellGlobalIdUTRA field descriptions
cellIdentity
UTRA Cell Identifier which is unique within the context of the identified PLMN as defined in TS 25.331 [19].
plmn-Identity
Identifies the PLMN of the cell as given by the common PLMN broadcast in the MIB, as defined in TS 25.331 [19].

-	CellGlobalIdGERAN
The IE CellGlobalIdGERAN specifies the Cell Global Identification (CGI), the globally unique identity of a cell in GERAN.
CellGlobalIdGERAN information element
-- ASN1START

CellGlobalIdGERAN ::=					SEQUENCE {
	plmn-Identity							PLMN-Identity,
	locationAreaCode						BIT STRING (SIZE (16)),
	cellIdentity						BIT STRING (SIZE (16))
}

-- ASN1STOP

CellGlobalIdGERAN field descriptions
cellIdentity
Cell Identifier which is unique within the context of the GERAN location area as defined in TS 23.003 [27].
locationAreaCode
A fixed length code identifying the location area within a PLMN as defined in TS 23.003 [27].
plmn-Identity
Identifies the PLMN of the cell, as defined in TS 23.003 [27]..

-	CellGlobalIdCDMA2000
The IE CellGlobalIdCDMA2000 specifies the Cell Global Identification (CGI), the globally unique identity of a cell in CDMA2000.
CellGlobalIdCDMA2000 information element
-- ASN1START

CellGlobalIdCDMA2000 ::=				CHOICE {
	cellGlobalId1XRTT						BIT STRING (SIZE (47)),
	cellGlobalIdHRPD						BIT STRING (SIZE (128))
}

-- ASN1STOP

CellGlobalIdCDMA2000 field descriptions
cellGlobalId1XRTT
Unique identifier for a CDMA2000 1xRTT cell, corresponds to BASEID, SID and NID parameters (in that order) defined in C.S0005 [25].
cellGlobalIdHRPD
Unique identifier for a CDMA2000 HRPD cell, corresponds to SECTOR ID parameter defined in C.S0024 [26, 14.9].

-	CSG-Identity
The IE CSG-Identity is used to identify a Closed Subscriber Group.
CSG-Identity information element
-- ASN1START

CSG-Identity ::=					BIT STRING (SIZE (27))

-- ASN1STOP

-	FreqBandIndicator
The IE FreqBandIndicator indicates the E-UTRA operating band as defined in TS 36.101 [42, table 5.5-1]. If an extension is signalled using the extended value range (as defined by IE FreqBandIndicator-v9e0), the UE shall only consider this extension (and hence ignore the corresponding original field, using the value range as defined by IE FreqBandIndicator i.e. without suffix, if signalled).
FreqBandIndicator information element
-- ASN1START

FreqBandIndicator ::=					INTEGER (1..maxFBI)

FreqBandIndicator-v9e0 ::=				INTEGER (maxFBI-Plus1..maxFBI2)

FreqBandIndicator-r11 ::=				INTEGER (1..maxFBI2)

-- ASN1STOP

NOTE:	For fields using the original value range, as defined by IE FreqBandIndicator i.e. without suffix, value maxFBI indicates that the frequency band is indicated by means of an extension. In such a case, UEs not supporting the extension consider the field to be set to a not supported value.

-	MobilityControlInfo
The IE MobilityControlInfo includes parameters relevant for network controlled mobility to/within E-UTRA.
MobilityControlInfo information element
-- ASN1START

MobilityControlInfo ::=		SEQUENCE {
	targetPhysCellId					PhysCellId,
	carrierFreq							CarrierFreqEUTRA					OPTIONAL,	-- Cond HO-toEUTRA2
	carrierBandwidth					CarrierBandwidthEUTRA				OPTIONAL,	-- Cond HO-toEUTRA
	additionalSpectrumEmission			AdditionalSpectrumEmission			OPTIONAL,	-- Cond HO-toEUTRA
	t304								ENUMERATED {
											ms50, ms100, ms150, ms200, ms500, ms1000,
											ms2000, spare1},
	newUE-Identity						C-RNTI,
	radioResourceConfigCommon			RadioResourceConfigCommon,
	rach-ConfigDedicated				RACH-ConfigDedicated				OPTIONAL,	-- Need OP
	...,
	[[	carrierFreq-v9e0				CarrierFreqEUTRA-v9e0				OPTIONAL	-- Need ON
	]],
	[[	drb-ContinueROHC-r11			ENUMERATED {true}					OPTIONAL	-- Cond HO
	]]
}

MobilityControlInfoSCG-r12 ::=		SEQUENCE {
	t307-r12							ENUMERATED {
											ms50, ms100, ms150, ms200, ms500, ms1000,
											ms2000, spare1},
	ue-IdentitySCG-r12					C-RNTI							OPTIONAL,	-- Cond SCGEst,
	rach-ConfigDedicated-r12			RACH-ConfigDedicated			OPTIONAL,	-- Need OP
	cipheringAlgorithmSCG-r12		CipheringAlgorithm-r12		OPTIONAL,	-- Need ON
	...
}

CarrierBandwidthEUTRA ::=			SEQUENCE {
	dl-Bandwidth						ENUMERATED {
												n6, n15, n25, n50, n75, n100, spare10,
												spare9, spare8, spare7, spare6, spare5,
												spare4, spare3, spare2, spare1},
	ul-Bandwidth						ENUMERATED {
												n6, n15, n25, n50, n75, n100, spare10,
												spare9, spare8, spare7, spare6, spare5,
												spare4, spare3, spare2, spare1}	OPTIONAL -- Need OP
}

CarrierFreqEUTRA ::=				SEQUENCE {
	dl-CarrierFreq						ARFCN-ValueEUTRA,
	ul-CarrierFreq						ARFCN-ValueEUTRA				OPTIONAL	-- Cond FDD
}

CarrierFreqEUTRA-v9e0 ::=			SEQUENCE {
	dl-CarrierFreq-v9e0					ARFCN-ValueEUTRA-r9,
	ul-CarrierFreq-v9e0					ARFCN-ValueEUTRA-r9			OPTIONAL	-- Cond FDD
}

-- ASN1STOP

MobilityControlInfo field descriptions
additionalSpectrumEmission
For a UE with no SCells configured for UL in the same band as the PCell, the UE shall apply the value for the PCell instead of the corresponding value from SystemInformationBlockType2 or SystemInformationBlockType1. For a UE with SCell(s) configured for UL in the same band as the PCell, the UE shall, in case all SCells configured for UL in that band are released after handover completion, apply the value for the PCell instead of the corresponding value from SystemInformationBlockType2 or SystemInformationBlockType1. The UE requirements related to IE AdditionalSpectrumEmission are defined in TS 36.101 [42, table 6.2.4.1].
carrierBandwidth
Provides the parameters Downlink bandwidth, and Uplink bandwidth, see TS 36.101 [42].
carrierFreq
Provides the EARFCN to be used by the UE in the target cell.
cipheringAlgorithmSCG
Indicates the ciphering algorithm to be used for SCG DRBs. E-UTRAN includes the field upon SCG change when one or more SCG DRBs are configured. Otherwise E-UTRAN does not include the field.
dl-Bandwidth
Parameter: Downlink bandwidth, see TS 36.101 [42].
drb-ContinueROHC 
This field indicates whether to continue or reset, for this handover, the header compression protocol context for the RLC UM bearers configured with the header compression protocol. Presence of the field indicates that the header compression protocol context continues while absence indicates that the header compression protocol context is reset. E-UTRAN includes the field only in case of a handover within the same eNB.
rach-ConfigDedicated
The dedicated random access parameters. If absent the UE applies contention based random access as specified in TS 36.321 [6].
t304
Timer T304 as described in section 7.3. ms50 corresponds with 50 ms, ms100 corresponds with 100 ms and so on.
t307
Timer T307 as described in section 7.3. ms50 corresponds with 50 ms, ms100 corresponds with 100 ms and so on.
ul-Bandwidth
Parameter: Uplink bandwidth, see TS 36.101 [42, table 5.6-1]. For TDD, the parameter is absent and it is equal to downlink bandwidth. If absent for FDD, apply the same value as applies for the downlink bandwidth.

Conditional presence
Explanation
FDD
The field is mandatory with default value (the default duplex distance defined for the concerned band, as specified in TS 36.101 [42]) in case of "FDD"; otherwise the field is not present.
HO
This field is optionally present, need OP, in case of handover within E-UTRA when the fullConfig is not included; otherwise the field is not present.
HO-toEUTRA
The field is mandatory present in case of inter-RAT handover to E-UTRA; otherwise the field is optionally present, need ON.
HO-toEUTRA2
The field is absent if carrierFreq-v9e0 is present. Otherwise it is mandatory present in case of inter-RAT handover to E-UTRA and optionally present, need ON, in all other cases.
SCGEst
This field is mandatory present in case of SCG establishment; otherwise the field is optionally present, need ON.

-	MobilityParametersCDMA2000 (1xRTT)
The MobilityParametersCDMA2000 contains the parameters provided to the UE for handover and (enhanced) CSFB to 1xRTT support, as defined in C.S0097 [53].
MobilityParametersCDMA2000 information element
-- ASN1START

MobilityParametersCDMA2000 ::=			OCTET STRING

-- ASN1STOP

-	MobilityStateParameters
The IE MobilityStateParameters contains parameters to determine UE mobility state.
MobilityStateParameters information element
-- ASN1START

MobilityStateParameters ::=			SEQUENCE {
	t-Evaluation						ENUMERATED {
											s30, s60, s120, s180, s240, spare3, spare2, spare1},
	t-HystNormal						ENUMERATED {
											s30, s60, s120, s180, s240, spare3, spare2, spare1},
	n-CellChangeMedium					INTEGER (1..16),
	n-CellChangeHigh					INTEGER (1..16)
}

-- ASN1STOP

MobilityStateParameters field descriptions
n-CellChangeHigh
The number of cell changes to enter high mobility state. Corresponds to NCR_H in TS 36.304 [4].
n-CellChangeMedium
The number of cell changes to enter medium mobility state. Corresponds to NCR_M in TS 36.304 [4].
t-Evaluation
The duration for evaluating criteria to enter mobility states. Corresponds to TCRmax in TS 36.304 [4]. Value in seconds, s30 corresponds to 30 s and so on.
t-HystNormal
The additional duration for evaluating criteria to enter normal mobility state. Corresponds to TCRmaxHyst in TS 36.304 [4]. Value in seconds, s30 corresponds to 30 s and so on.

-	MultiBandInfoList
MultiBandInfoList information element
-- ASN1START

MultiBandInfoList ::=	SEQUENCE (SIZE (1..maxMultiBands)) OF FreqBandIndicator

MultiBandInfoList-v9e0 ::=	SEQUENCE (SIZE (1..maxMultiBands)) OF MultiBandInfo-v9e0

MultiBandInfoList-v10j0 ::=	SEQUENCE (SIZE (1..maxMultiBands)) OF NS-PmaxList-r10

MultiBandInfoList-r11 ::=	SEQUENCE (SIZE (1..maxMultiBands)) OF FreqBandIndicator-r11

MultiBandInfo-v9e0 ::=		SEQUENCE {
	freqBandIndicator-v9e0				FreqBandIndicator-v9e0		OPTIONAL	-- Need OP
}

-- ASN1STOP

-	NS-PmaxList
The IE NS-PmaxList concerns a list of additionalPmax and additionalSpectrumEmission as defined in TS 36.101 [42, table 6.2.4-1] for a given frequency band. E-UTRAN does not include the same value of additionalSpectrumEmission in SystemInformationType2 within this list.
NS-PmaxList information element
-- ASN1START

NS-PmaxList-r10 ::=				SEQUENCE (SIZE (1..maxNS-Pmax-r10)) OF NS-PmaxValue-r10

NS-PmaxValue-r10 ::=			SEQUENCE {
	additionalPmax-r10					P-Max							OPTIONAL,	-- Need OP
	additionalSpectrumEmission			AdditionalSpectrumEmission
}

-- ASN1STOP

-	PhysCellId
The IE PhysCellId is used to indicate the physical layer identity of the cell, as defined in TS 36.211 [21].
PhysCellId information element
-- ASN1START

PhysCellId ::=						INTEGER (0..503)

-- ASN1STOP

-	PhysCellIdRange
The IE PhysCellIdRange is used to encode either a single or a range of physical cell identities. The range is encoded by using a start value and by indicating the number of consecutive physical cell identities (including start) in the range. For fields comprising multiple occurrences of PhysCellIdRange, E-UTRAN may configure overlapping ranges of physical cell identities.
PhysCellIdRange information element
-- ASN1START

PhysCellIdRange ::=				SEQUENCE {
	start							PhysCellId,
	range							ENUMERATED {
										n4, n8, n12, n16, n24, n32, n48, n64, n84,
										n96, n128, n168, n252, n504, spare2,
										spare1} 					OPTIONAL	-- Need OP
}

-- ASN1STOP

PhysCellIdRange field descriptions
range
Indicates the number of physical cell identities in the range (including start). Value n4 corresponds with 4, n8 corresponds with 8 and so on. The UE shall apply value 1 in case the field is absent, in which case only the physical cell identity value indicated by start applies.
start
Indicates the lowest physical cell identity in the range.

-	PhysCellIdRangeUTRA-FDDList
The IE PhysCellIdRangeUTRA-FDDList is used to encode one or more of PhysCellIdRangeUTRA-FDD. While the IE PhysCellIdRangeUTRA-FDD is used to encode either a single physical layer identity or a range of physical layer identities, i.e. primary scrambling codes. Each range is encoded by using a start value and by indicating the number of consecutive physical cell identities (including start) in the range.
PhysCellIdRangeUTRA-FDDList information element
-- ASN1START

PhysCellIdRangeUTRA-FDDList-r9::=		SEQUENCE (SIZE (1..maxPhysCellIdRange-r9)) OF PhysCellIdRangeUTRA-FDD-r9

PhysCellIdRangeUTRA-FDD-r9 ::=			SEQUENCE {
		start-r9							PhysCellIdUTRA-FDD,
		range-r9							INTEGER (2..512)				OPTIONAL	-- Need OP
}

-- ASN1STOP

PhysCellIdRangeUTRA-FDDList field descriptions
range
Indicates the number of primary scrambling codes in the range (including start). The UE shall apply value 1 in case the field is absent, in which case only the primary scrambling code value indicated by start applies.
start
Indicates the lowest primary scrambling code in the range.

-	PhysCellIdCDMA2000
The IE PhysCellIdCDMA2000 identifies the PNOffset that represents the "Physical cell identity" in CDMA2000.
PhysCellIdCDMA2000 information element
-- ASN1START

PhysCellIdCDMA2000 ::=			INTEGER (0..maxPNOffset)

-- ASN1STOP

-	PhysCellIdGERAN
The IE PhysCellIdGERAN contains the Base Station Identity Code (BSIC).
PhysCellIdGERAN information element
-- ASN1START

PhysCellIdGERAN ::=				SEQUENCE {
	networkColourCode					BIT STRING (SIZE (3)),
	baseStationColourCode				BIT STRING (SIZE (3))
}

-- ASN1STOP

PhysCellIdGERAN field descriptions
baseStationColourCode
Base station Colour Code as defined in TS 23.003 [27].
networkColourCode
Network Colour Code as defined in TS 23.003 [27].

-	PhysCellIdUTRA-FDD
The IE PhysCellIdUTRA-FDD is used to indicate the physical layer identity of the cell, i.e. the primary scrambling code, as defined in TS 25.331 [19].
PhysCellIdUTRA-FDD information element
-- ASN1START

PhysCellIdUTRA-FDD ::=				INTEGER (0..511)

-- ASN1STOP

-	PhysCellIdUTRA-TDD
The IE PhysCellIdUTRA-TDD is used to indicate the physical layer identity of the cell, i.e. the cell parameters ID (TDD), as specified in TS 25.331 [19]. Also corresponds to the Initial Cell Parameter Assignment in TS 25.223 [46].
PhysCellIdUTRA-TDD information element
-- ASN1START

PhysCellIdUTRA-TDD ::=				INTEGER (0..127)

-- ASN1STOP

-	PLMN-Identity
The IE PLMN-Identity identifies a Public Land Mobile Network. Further information regarding how to set the IE are specified in TS 23.003 [27].
PLMN-Identity information element
-- ASN1START

PLMN-Identity ::=					SEQUENCE {
	mcc									MCC					OPTIONAL,					-- Cond MCC
	mnc									MNC
}

MCC ::=								SEQUENCE (SIZE (3)) OF
											MCC-MNC-Digit

MNC ::=								SEQUENCE (SIZE (2..3)) OF
											MCC-MNC-Digit

MCC-MNC-Digit ::=					INTEGER (0..9)


-- ASN1STOP

PLMN-Identity field descriptions
mcc
The first element contains the first MCC digit, the second element the second MCC digit and so on. If the field is absent, it takes the same value as the mcc of the immediately preceding IE PLMN-Identity. See TS 23.003 [27].
mnc
The first element contains the first MNC digit, the second element the second MNC digit and so on. See TS 23.003 [27].

Conditional presence
Explanation
MCC
This IE is mandatory when PLMN-Identity is included in CellGlobalIdEUTRA, in CellGlobalIdUTRA, in CellGlobalIdGERAN or in RegisteredMME. This IE is also mandatory in the first occurrence of the IE PLMN-Identity within the IE PLMN-IdentityList. Otherwise it is optional, need OP.

-	PLMN-IdentityList3
Includes a list of PLMN identities.
PLMN-IdentityList3 information element
-- ASN1START

PLMN-IdentityList3-r11 ::=				SEQUENCE (SIZE (1..16)) OF PLMN-Identity

-- ASN1STOP

-	PreRegistrationInfoHRPD
-- ASN1START

PreRegistrationInfoHRPD ::=			SEQUENCE {
	preRegistrationAllowed				BOOLEAN,
	preRegistrationZoneId				PreRegistrationZoneIdHRPD	OPTIONAL, -- cond PreRegAllowed
	secondaryPreRegistrationZoneIdList	SecondaryPreRegistrationZoneIdListHRPD	OPTIONAL -- Need OR
}

SecondaryPreRegistrationZoneIdListHRPD ::=	SEQUENCE (SIZE (1..2)) OF PreRegistrationZoneIdHRPD

PreRegistrationZoneIdHRPD ::=			INTEGER (0..255)

-- ASN1STOP

PreRegistrationInfoHRPD field descriptions
preRegistrationAllowed
TRUE indicates that a UE shall perform a CDMA2000 HRPD pre-registration if the UE does not have a valid / current pre-registration. FALSE indicates that the UE is not allowed to perform CDMA2000 HRPD pre-registration in the current cell.
preRegistrationZoneID
ColorCode (see C.S0024 [26], C.S0087 [44]) of the CDMA2000 Reference Cell corresponding to the HRPD sector under the HRPD AN that is configured for this LTE cell. It is used to control when the UE should register or re-register.
secondaryPreRegistrationZoneIdList
List of SecondaryColorCodes (see C.S0024 [26], C.S0087 [44]) of the CDMA2000 Reference Cell corresponding to the HRPD sector under the HRPD AN that is configured for this LTE cell. They are used to control when the UE should re-register.

Conditional presence
Explanation
PreRegAllowed
The field is mandatory in case the preRegistrationAllowed is set to true. Otherwise the field is not present and the UE shall delete any existing value for this field.

-	Q-QualMin
The IE Q-QualMin is used to indicate for cell selection/ re-selection the required minimum received RSRQ level in the (E-UTRA) cell. Corresponds to parameter Qqualmin in 36.304 [4]. Actual value Qqualmin = IE value [dB].
Q-QualMin information element
-- ASN1START

Q-QualMin-r9 ::=					INTEGER (-34..-3)

-- ASN1STOP

-	Q-RxLevMin
The IE Q-RxLevMin is used to indicate for cell selection/ re-selection the required minimum received RSRP level in the (E-UTRA) cell. Corresponds to parameter Qrxlevmin in 36.304 [4]. Actual value Qrxlevmin = IE value * 2 [dBm].
Q-RxLevMin information element
-- ASN1START

Q-RxLevMin ::=						INTEGER (-70..-22)

-- ASN1STOP

-	Q-OffsetRange
The IE Q-OffsetRange is used to indicate a cell, CSI-RS resource or frequency specific offset to be applied when evaluating candidates for cell re-selection or when evaluating triggering conditions for measurement reporting. The value in dB. Value dB-24 corresponds to -24 dB, dB-22 corresponds to -22 dB and so on.
Q- OffsetRange information element
-- ASN1START

Q-OffsetRange ::=						ENUMERATED {
												dB-24, dB-22, dB-20, dB-18, dB-16, dB-14,
												dB-12, dB-10, dB-8, dB-6, dB-5, dB-4, dB-3,
												dB-2, dB-1, dB0, dB1, dB2, dB3, dB4, dB5,
												dB6, dB8, dB10, dB12, dB14, dB16, dB18,
												dB20, dB22, dB24}

-- ASN1STOP

-	Q-OffsetRangeInterRAT
The IE Q-OffsetRangeInterRAT is used to indicate a frequency specific offset to be applied when evaluating triggering conditions for measurement reporting. The value in dB.
Q-OffsetRangeInterRAT information element
-- ASN1START

Q-OffsetRangeInterRAT ::=					INTEGER (-15..15)

-- ASN1STOP

-	ReselectionThreshold
The IE ReselectionThreshold is used to indicate an Rx level threshold for cell reselection. Actual value of threshold = IE value * 2 [dB].
ReselectionThreshold information element
-- ASN1START

ReselectionThreshold ::=				INTEGER (0..31)

-- ASN1STOP

-	ReselectionThresholdQ
The IE ReselectionThresholdQ is used to indicate a quality level threshold for cell reselection. Actual value of threshold = IE value [dB].
ReselectionThresholdQ information element
-- ASN1START

ReselectionThresholdQ-r9 ::=			INTEGER (0..31)

-- ASN1STOP

-	SCellIndex
The IE SCellIndex concerns a short identity, used to identify an SCell.
SCellIndex information element
-- ASN1START

SCellIndex-r10 ::=						INTEGER (1..7)
SCellIndex-v13xy ::=					INTEGER (8..31)
SCellIndex-r13 ::=						INTEGER (1..31)

-- ASN1STOP

-	ServCellIndex
The IE ServCellIndex concerns a short identity, used to identify a serving cell (i.e. the PCell or an SCell). Value 0 applies for the PCell, while the SCellIndex that has previously been assigned applies for SCells.
ServCellIndex information element
-- ASN1START

ServCellIndex-r10 ::=					INTEGER (0..7)
ServCellIndex-v13xy ::=					INTEGER (8..31)
ServCellIndexFull-r13 ::=				INTEGER (0..31)

-- ASN1STOP

-	SpeedStateScaleFactors
The IE SpeedStateScaleFactors concerns factors, to be applied when the UE is in medium or high speed state, used for scaling a mobility control related parameter.
SpeedStateScaleFactors information element
-- ASN1START

SpeedStateScaleFactors ::=			SEQUENCE {
	sf-Medium							ENUMERATED {oDot25, oDot5, oDot75, lDot0},
	sf-High								ENUMERATED {oDot25, oDot5, oDot75, lDot0}
}
-- ASN1STOP

SpeedStateScaleFactors field descriptions
sf-High
The concerned mobility control related parameter is multiplied with this factor if the UE is in High Mobility state as defined in TS 36.304 [4]. Value oDot25 corresponds to 0.25, oDot5 corresponds to 0.5 , oDot75 corresponds to 0.75 and so on.
sf-Medium
The concerned mobility control related parameter is multiplied with this factor if the UE is in Medium Mobility state as defined in TS 36.304 [4]. Value oDot25 corresponds to 0.25, oDot5 corresponds to 0.5 , oDot75 corresponds to 0.75 and so on.

-	SystemInfoListGERAN
The IE SystemInfoListGERAN contains system information of a GERAN cell.
SystemInfoListGERAN information element
-- ASN1START

SystemInfoListGERAN ::=				SEQUENCE (SIZE (1..maxGERAN-SI)) OF
										OCTET STRING (SIZE (1..23))

-- ASN1STOP

SystemInfoListGERAN field descriptions
SystemInfoListGERAN
Each OCTET STRING contains one System Information (SI) message as defined in TS 44.018 [45, table 9.1.1] excluding the L2 Pseudo Length, the RR management Protocol Discriminator and the Skip Indicator or a complete Packet System Information (PSI) message as defined in TS 44.060 [36, table 11.2.1]. 

-	SystemTimeInfoCDMA2000
The IE SystemTimeInfoCDMA2000 informs the UE about the absolute time in the current cell. The UE uses this absolute time knowledge to derive the CDMA2000 Physical cell identity, expressed as PNOffset, of neighbour CDMA2000 cells.
NOTE:	The UE needs the CDMA2000 system time with a certain level of accuracy for performing measurements as well as for communicating with the CDMA2000 network (HRPD or 1xRTT).
SystemTimeInfoCDMA2000 information element
-- ASN1START

SystemTimeInfoCDMA2000 ::=			SEQUENCE {
	cdma-EUTRA-Synchronisation			BOOLEAN,
	cdma-SystemTime						CHOICE {
		synchronousSystemTime				BIT STRING (SIZE (39)),
		asynchronousSystemTime				BIT STRING (SIZE (49))
	}
}

-- ASN1STOP

SystemTimeInfoCDMA2000 field descriptions
asynchronousSystemTime
The CDMA2000 system time corresponding to the SFN boundary at or after the ending boundary of the SI-Window in which SystemInformationBlockType8 is transmitted. E-UTRAN includes this field if the E-UTRA frame boundary is not aligned to the start of CDMA2000 system time. This field size is 49 bits and the unit is 8 CDMA chips based on 1.2288 Mcps.
cdma-EUTRA-Synchronisation
TRUE indicates that there is no drift in the timing between E-UTRA and CDMA2000. FALSE indicates that the timing between E-UTRA and CDMA2000 can drift. NOTE 1
synchronousSystemTime
CDMA2000 system time corresponding to the SFN boundary at or after the ending boundary of the SI-window in which SystemInformationBlockType8 is transmitted. E-UTRAN includes this field if the E-UTRA frame boundary is aligned to the start of CDMA2000 system time. This field size is 39 bits and the unit is 10 ms based on a 1.2288 Mcps chip rate.

NOTE 1:	The following table shows the recommended combinations of the cdma-EUTRA-Synchronisation field and the choice of cdma-SystemTime included by E-UTRAN for FDD and TDD:

FDD/TDD
cdma-EUTRA-Synchronisation
synchronousSystemTime
asynchronousSystemTime
FDD
FALSE
Not Recommended
Recommended
FDD
TRUE
Recommended
Recommended
TDD
FALSE
Not Recommended
Recommended
TDD
TRUE
Recommended
Recommended

-	TrackingAreaCode
The IE TrackingAreaCode is used to identify a tracking area within the scope of a PLMN, see TS 24.301 [35].
TrackingAreaCode information element
-- ASN1START

TrackingAreaCode ::=				BIT STRING (SIZE (16))

-- ASN1STOP

-	T-Reselection
The IE T-Reselection concerns the cell reselection timer TreselectionRAT for E-UTRA, UTRA, GERAN or CDMA2000. Value in seconds.
T-Reselection information element
-- ASN1START

T-Reselection ::=					INTEGER (0..7)

-- ASN1STOP

6.3.5	Measurement information elements
-	AllowedMeasBandwidth
The IE AllowedMeasBandwidth is used to indicate the maximum allowed measurement bandwidth on a carrier frequency as defined by the parameter Transmission Bandwidth Configuration "NRB" TS 36.104 [47]. The values mbw6, mbw15, mbw25, mbw50, mbw75, mbw100 indicate 6, 15, 25, 50, 75 and 100 resource blocks respectively.
AllowedMeasBandwidth information element
-- ASN1START

AllowedMeasBandwidth ::=				ENUMERATED {mbw6, mbw15, mbw25, mbw50, mbw75, mbw100}

-- ASN1STOP

-	CSI-RSRP-Range
The IE CSI-RSRP-Range specifies the value range used in CSI-RSRP measurements and thresholds. Integer value for CSI-RSRP measurements according to mapping table in TS 36.133 [16].
CSI-RSRP-Range information element
-- ASN1START

CSI-RSRP-Range-r12 ::=						INTEGER(0..97)

-- ASN1STOP

-	Hysteresis
The IE Hysteresis is a parameter used within the entry and leave condition of an event triggered reporting condition. The actual value is IE value * 0.5 dB.
Hysteresis information element
-- ASN1START

Hysteresis ::=							INTEGER (0..30)

-- ASN1STOP

-	LocationInfo
The IE LocationInfo is used to transfer detailed location information available at the UE to correlate measurements and UE position information.
LocationInfo information element
-- ASN1START

LocationInfo-r10 ::=	SEQUENCE {
	locationCoordinates-r10					CHOICE {
		ellipsoid-Point-r10						OCTET STRING,
		ellipsoidPointWithAltitude-r10			OCTET STRING,
	...,
		ellipsoidPointWithUncertaintyCircle-r11					OCTET STRING,
		ellipsoidPointWithUncertaintyEllipse-r11				OCTET STRING,
		ellipsoidPointWithAltitudeAndUncertaintyEllipsoid-r11	OCTET STRING,
		ellipsoidArc-r11			 							OCTET STRING,
		polygon-r11												OCTET STRING
	},
	horizontalVelocity-r10					OCTET STRING				OPTIONAL,
	gnss-TOD-msec-r10						OCTET STRING				OPTIONAL,
	...
}

-- ASN1STOP

LocationInfo field descriptions
ellipsoidArc
Parameter EllipsoidArc defined in TS36.355 [54]. The first/leftmost bit of the first octet contains the most significant bit.
ellipsoid-Point
Parameter Ellipsoid-Point defined in TS36.355 [54]. The first/leftmost bit of the first octet contains the most significant bit.
ellipsoidPointWithAltitude
Parameter EllipsoidPointWithAltitude defined in TS36.355 [54]. The first/leftmost bit of the first octet contains the most significant bit.
ellipsoidPointWithAltitudeAndUncertaintyEllipsoid 
Parameter EllipsoidPointWithAltitudeAndUncertaintyEllipsoid defined in TS36.355 [54]. The first/leftmost bit of the first octet contains the most significant bit.
ellipsoidPointWithUncertaintyCircle
Parameter Ellipsoid-PointWithUncertaintyCircle defined in TS36.355 [54]. The first/leftmost bit of the first octet contains the most significant bit.
ellipsoidPointWithUncertaintyEllipse
Parameter EllipsoidPointWithUncertaintyEllipse defined in TS36.355 [54]. The first/leftmost bit of the first octet contains the most significant bit.
gnss-TOD-msec
Parameter Gnss-TOD-msec defined in TS36.355 [54]. The first/leftmost bit of the first octet contains the most significant bit.
horizontalVelocity
Parameter HorizontalVelocity defined in TS36.355 [54]. The first/leftmost bit of the first octet contains the most significant bit.
polygon
Parameter Polygon defined in TS36.355 [54]. The first/leftmost bit of the first octet contains the most significant bit.

-	MBSFN-RSRQ-Range
The IE MBSFN-RSRQ-Range specifies the value range used in MBSFN RSRQ measurements. Integer value for MBSFN RSRQ measurements according to mapping table in TS 36.133 [16].
MBSFN-RSRQ-Range information element
-- ASN1START

MBSFN-RSRQ-Range-r12 ::=				INTEGER(0..31)
-- ASN1STOP

-	MeasConfig
The IE MeasConfig specifies measurements to be performed by the UE, and covers intra-frequency, inter-frequency and inter-RAT mobility as well as configuration of measurement gaps.
MeasConfig information element
-- ASN1START

MeasConfig ::=						SEQUENCE {
	-- Measurement objects
	measObjectToRemoveList				MeasObjectToRemoveList				OPTIONAL,	-- Need ON
	measObjectToAddModList				MeasObjectToAddModList				OPTIONAL,	-- Need ON
	-- Reporting configurations
	reportConfigToRemoveList			ReportConfigToRemoveList			OPTIONAL,	-- Need ON
	reportConfigToAddModList			ReportConfigToAddModList			OPTIONAL,	-- Need ON
	-- Measurement identities
	measIdToRemoveList					MeasIdToRemoveList					OPTIONAL,	-- Need ON
	measIdToAddModList					MeasIdToAddModList					OPTIONAL,	-- Need ON
	-- Other parameters
	quantityConfig						QuantityConfig						OPTIONAL,	-- Need ON
	measGapConfig						MeasGapConfig						OPTIONAL,	-- Need ON
	s-Measure							RSRP-Range							OPTIONAL,	-- Need ON
	preRegistrationInfoHRPD				PreRegistrationInfoHRPD				OPTIONAL, 	-- Need OP
	speedStatePars			CHOICE {
		release								NULL,
		setup								SEQUENCE {
			mobilityStateParameters				MobilityStateParameters,
			timeToTrigger-SF					SpeedStateScaleFactors
		}
	}																		OPTIONAL,	-- Need ON
	...,
	[[	measObjectToAddModList-v9e0			MeasObjectToAddModList-v9e0		OPTIONAL	-- Need ON
	]],
	[[	allowInterruptions-r11				BOOLEAN							OPTIONAL	-- Need ON
	]],
	[[	measScaleFactor-r12			CHOICE {
			release						NULL,
			setup						MeasScaleFactor-r12
		}																OPTIONAL,	-- Need ON
		measIdToRemoveListExt-r12			MeasIdToRemoveListExt-r12		OPTIONAL,	-- Need ON
		measIdToAddModListExt-r12			MeasIdToAddModListExt-r12		OPTIONAL,	-- Need ON
		measRSRQ-OnAllSymbols-r12		BOOLEAN							OPTIONAL	-- Need ON
	]],
	[[	ul-DelayConfig-r13			UL-DelayConfig-r13		OPTIONAL		-- Need ON
	]]
}

MeasIdToRemoveList ::=				SEQUENCE (SIZE (1..maxMeasId)) OF MeasId

MeasIdToRemoveListExt-r12 ::=		SEQUENCE (SIZE (1..maxMeasId)) OF MeasId-v1250

MeasObjectToRemoveList ::=			SEQUENCE (SIZE (1..maxObjectId)) OF MeasObjectId

ReportConfigToRemoveList ::=		SEQUENCE (SIZE (1..maxReportConfigId)) OF ReportConfigId

-- ASN1STOP

MeasConfig field descriptions
allowInterruptions
Value TRUE indicates that the UE is allowed to cause interruptions to serving cells when performing measurements of deactivated SCell carriers for measCycleSCell of less than 640ms, as specified in TS 36.133 [16]. E-UTRAN enables this field only when an SCell is configured.
measGapConfig
Used to setup and release measurement gaps.
measIdToRemoveList
List of measurement identities to remove. Field measIdToRemoveListExt includes additional measurement identities i.e. extends the size of the measurement identity list using the general principles specified in 5.1.2.
measObjectToAddModList
If E-UTRAN includes measObjectToAddModList-v9e0 it includes the same number of entries, and listed in the same order, as in measObjectToAddModList (i.e. without suffix).
measObjectToRemoveList
List of measurement objects to remove.
measRSRQ-OnAllSymbols
Value TRUE indicates that the UE shall, when performing RSRQ measurements, perform RSRQ measurement on all OFDM symbols in accordance with TS 36.214 [48]. If widebandRSRQ-Meas is enabled for the frequency in MeasObjectEUTRA, the UE shall, when performing RSRQ measurements, perform RSRQ measurement on all OFDM symbols with wider bandwidth for concerned frequency in accordance with TS 36.214 [48].
measScaleFactor
Even if reducedMeasPerformance is not included in any measObjectEUTRA or measObjectUTRA, E-UTRAN may configure this field. The UE behavior is specified in TS 36.133 [16].
PreRegistrationInfoHRPD
The CDMA2000 HRPD Pre-Registration Information tells the UE if it should pre-register with the CDMA2000 HRPD network and identifies the Pre-registration zone to the UE.
reportConfigToRemoveList
List of measurement reporting configurations to remove.
s-Measure
PCell quality threshold controlling whether or not the UE is required to perform measurements of intra-frequency, inter-frequency and inter-RAT neighbouring cells. Value "0" indicates to disable s-Measure.
timeToTrigger-SF
The timeToTrigger in ReportConfigEUTRA and in ReportConfigInterRAT are multiplied with the scaling factor applicable for the UE's speed state.
ul-DelayConfig
Used to setup and release UL PDCP Packet Delay per QCI measurement.

-	MeasDS-Config
The IE MeasDS-Config specifies information applicable for discovery signals measurement.
MeasDS-Config information elements
-- ASN1START

MeasDS-Config-r12 ::=			CHOICE {
	release							NULL,
	setup							SEQUENCE {
		dmtc-PeriodOffset-r12			CHOICE {
			ms40-r12						INTEGER(0..39),
			ms80-r12						INTEGER(0..79),
			ms160-r12						INTEGER(0..159),
			...
		},
		ds-OccasionDuration-r12		CHOICE {
			durationFDD-r12 				INTEGER(1..maxDS-Duration-r12),
			durationTDD-r12 				INTEGER(2..maxDS-Duration-r12)
		},
		measCSI-RS-ToRemoveList-r12	MeasCSI-RS-ToRemoveList-r12	OPTIONAL,	-- Need ON
		measCSI-RS-ToAddModList-r12	MeasCSI-RS-ToAddModList-r12	OPTIONAL,	-- Need ON
		...
	}
}

MeasCSI-RS-ToRemoveList-r12 ::=	SEQUENCE (SIZE (1..maxCSI-RS-Meas-r12)) OF MeasCSI-RS-Id-r12

MeasCSI-RS-ToAddModList-r12 ::=	SEQUENCE (SIZE (1..maxCSI-RS-Meas-r12)) OF MeasCSI-RS-Config-r12

MeasCSI-RS-Id-r12 ::=			INTEGER (1..maxCSI-RS-Meas-r12)

MeasCSI-RS-Config-r12 ::=		SEQUENCE {
	measCSI-RS-Id-r12				MeasCSI-RS-Id-r12,
	physCellId-r12					INTEGER (0..503),
	scramblingIdentity-r12			INTEGER (0..503),
	resourceConfig-r12				INTEGER (0..31),
	subframeOffset-r12				INTEGER (0..4),
	csi-RS-IndividualOffset-r12		Q-OffsetRange,
	...
}

-- ASN1STOP

MeasDS-Config field descriptions
csi-RS-IndividualOffset
CSI-RS individual offset applicable to a specific CSI-RS resource. Value dB-24 corresponds to -24 dB, dB-22 corresponds to -22 dB and so on.
dmtc-PeriodOffset
Indicates the discovery signals measurement timing configuration (DMTC) periodicity (dmtc-Periodicity) and offset (dmtc-Offset) for this frequency. For DMTC periodicity, value ms40 corresponds to 40ms, ms80 corresponds to 80ms and so on. The value of DMTC offset is in number of subframe(s). The duration of a DMTC occasion is 6ms.
ds-OccasionDuration
Indicates the duration of discovery signal occasion for this frequency. Discovery signal occasion duration is common for all cells transmitting discovery signals on one frequency. The field ds-OccasionDuration is set to values 1 for an LAA SCell.
measCSI-RS-ToAddModList
List of CSI-RS resources to add/ modify in the CSI-RS resource list for discovery signals measurement.
measCSI-RS-ToRemoveList
List of CSI-RS resources to remove from the CSI-RS resource list for discovery signals measurement.
physCellId
Indicates the physical cell identity where UE may assume that the CSI-RS and the PSS/SSS/CRS corresponding to the indicated physical cell identity are quasi co-located with respect to average delay and doppler shift.
resourceConfig
Parameter: CSI reference signal configuration, see TS 36.211 [21, table 6.10.5.2-1 and 6.10.5.2-2]. The values {0, 4, 5, 9, 10, 11, 18, 19} are not applicable for an LAA SCell.
scramblingIdentity
Parameter: Pseudo-random sequence generator parameter, , see TS 36.213 [23, 7.2.5].
subframeOffset
Indicates the subframe offset between SSS of the cell indicated by physCellId and the CSI-RS resource in a discovery signal occasion. The field subframeOffset is set to values 0 for an LAA SCell.


-	MeasGapConfig
The IE MeasGapConfig specifies the measurement gap configuration and controls setup/ release of measurement gaps.
MeasGapConfig information element
-- ASN1START

MeasGapConfig ::=					CHOICE {
	release								NULL,
	setup								SEQUENCE {
		gapOffset							CHOICE {
				gp0									INTEGER (0..39),
				gp1									INTEGER (0..79),
				...
		}
	}
}

-- ASN1STOP

MeasGapConfig field descriptions
gapOffset
Value gapOffset of gp0 corresponds to gap offset of Gap Pattern Id "0" with MGRP = 40ms, gapOffset of gp1 corresponds to gap offset of Gap Pattern Id "1" with MGRP = 80ms. Also used to specify the measurement gap pattern to be applied, as defined in TS 36.133 [16].

-	MeasId
The IE MeasId is used to identify a measurement configuration, i.e., linking of a measurement object and a reporting configuration.
MeasId information element
-- ASN1START

MeasId ::=							INTEGER (1..maxMeasId)

MeasId-v1250 ::=					INTEGER (maxMeasId-Plus1..maxMeasId-r12)

-- ASN1STOP

-	MeasIdToAddModList
The IE MeasIdToAddModList concerns a list of measurement identities to add or modify, with for each entry the measId, the associated measObjectId and the associated reportConfigId. Field measIdToAddModListExt includes additional measurement identities i.e. extends the size of the measurement identity list using the general principles specified in 5.1.2.
MeasIdToAddModList information element
-- ASN1START

MeasIdToAddModList ::=				SEQUENCE (SIZE (1..maxMeasId)) OF MeasIdToAddMod

MeasIdToAddModListExt-r12 ::=		SEQUENCE (SIZE (1..maxMeasId)) OF MeasIdToAddModExt-r12

MeasIdToAddMod ::=	SEQUENCE {
	measId								MeasId,
	measObjectId						MeasObjectId,
	reportConfigId						ReportConfigId
}

MeasIdToAddModExt-r12 ::=	SEQUENCE {
	measId-v1250						MeasId-v1250,
	measObjectId-r12					MeasObjectId,
	reportConfigId-r12					ReportConfigId
}

-- ASN1STOP

-	MeasObjectCDMA2000
The IE MeasObjectCDMA2000 specifies information applicable for inter-RAT CDMA2000 neighbouring cells.
MeasObjectCDMA2000 information element
-- ASN1START

MeasObjectCDMA2000 ::=				SEQUENCE {
	cdma2000-Type						CDMA2000-Type,
	carrierFreq							CarrierFreqCDMA2000,
	searchWindowSize					INTEGER (0..15)						OPTIONAL,	-- Need ON
	offsetFreq							Q-OffsetRangeInterRAT				DEFAULT 0,
	cellsToRemoveList					CellIndexList						OPTIONAL,	-- Need ON
	cellsToAddModList					CellsToAddModListCDMA2000			OPTIONAL,	-- Need ON
	cellForWhichToReportCGI				PhysCellIdCDMA2000					OPTIONAL,	-- Need ON
	...
}

CellsToAddModListCDMA2000 ::=		SEQUENCE (SIZE (1..maxCellMeas)) OF CellsToAddModCDMA2000

CellsToAddModCDMA2000 ::=	SEQUENCE {
	cellIndex							INTEGER (1..maxCellMeas),
	physCellId							PhysCellIdCDMA2000
}

-- ASN1STOP

MeasObjectCDMA2000 field descriptions
carrierInfo
Identifies CDMA2000 carrier frequency for which this configuration is valid.
cdma2000-Type
The type of CDMA2000 network: CDMA2000 1xRTT or CDMA2000 HRPD.
cellIndex
Entry index in the neighbouring cell list.
cellsToAddModList
List of cells to add/ modify in the neighbouring cell list.
cellsToRemoveList
List of cells to remove from the neighbouring cell list.
physCellId
CDMA2000 Physical cell identity of a cell in neighbouring cell list expressed as PNOffset.
searchWindowSize
Provides the search window size to be used by the UE for the neighbouring pilot, see C.S0005 [25].

-	MeasObjectEUTRA
The IE MeasObjectEUTRA specifies information applicable for intra-frequency or inter-frequency E-UTRA cells.
MeasObjectEUTRA information element
-- ASN1START

MeasObjectEUTRA ::=					SEQUENCE {
	carrierFreq							ARFCN-ValueEUTRA,
	allowedMeasBandwidth				AllowedMeasBandwidth,
	presenceAntennaPort1				PresenceAntennaPort1,
	neighCellConfig						NeighCellConfig,
	offsetFreq							Q-OffsetRange				DEFAULT dB0,
	-- Cell list
	cellsToRemoveList					CellIndexList				OPTIONAL,		-- Need ON
	cellsToAddModList					CellsToAddModList			OPTIONAL,		-- Need ON
	-- Black list
	blackCellsToRemoveList				CellIndexList				OPTIONAL,		-- Need ON
	blackCellsToAddModList				BlackCellsToAddModList		OPTIONAL,		-- Need ON
	cellForWhichToReportCGI				PhysCellId					OPTIONAL,		-- Need ON
	...,
	[[measCycleSCell-r10				MeasCycleSCell-r10		OPTIONAL,		-- Need ON
		measSubframePatternConfigNeigh-r10	MeasSubframePatternConfigNeigh-r10	OPTIONAL							-- Need ON
	]],
	[[widebandRSRQ-Meas-r11				BOOLEAN	OPTIONAL		-- Cond WB-RSRQ
	]],
	[[	altTTT-CellsToRemoveList-r12	CellIndexList				OPTIONAL,		-- Need ON
		altTTT-CellsToAddModList-r12	AltTTT-CellsToAddModList-r12	OPTIONAL,		-- Need ON
		t312-r12						CHOICE {
			release							NULL,
			setup							ENUMERATED {ms0, ms50, ms100, ms200,
											 ms300, ms400, ms500, ms1000}
		}														OPTIONAL,		-- Need ON
		reducedMeasPerformance-r12		BOOLEAN 					OPTIONAL,	 	-- Need ON
		measDS-Config-r12				MeasDS-Config-r12			OPTIONAL		-- Need ON
	]],
	[[	
		whiteCellsToRemoveList-r13		CellIndexList				OPTIONAL,		-- Need ON
		whiteCellsToAddModList-r13		WhiteCellsToAddModList-r13	OPTIONAL,		-- Need ON
		measRSSI-Config-r13				MeasRSSI-Config-r13			OPTIONAL		-- Need ON
	]]
}

MeasObjectEUTRA-v9e0 ::=			SEQUENCE {
	carrierFreq-v9e0					ARFCN-ValueEUTRA-v9e0
}

CellsToAddModList ::=				SEQUENCE (SIZE (1..maxCellMeas)) OF CellsToAddMod

CellsToAddMod ::=	SEQUENCE {
	cellIndex							INTEGER (1..maxCellMeas),
	physCellId							PhysCellId,
	cellIndividualOffset				Q-OffsetRange
}

BlackCellsToAddModList ::=			SEQUENCE (SIZE (1..maxCellMeas)) OF BlackCellsToAddMod

BlackCellsToAddMod ::=	SEQUENCE {
	cellIndex							INTEGER (1..maxCellMeas),
	physCellIdRange						PhysCellIdRange
}

MeasCycleSCell-r10 ::=				ENUMERATED {sf160, sf256, sf320, sf512,
													sf640, sf1024, sf1280, spare1}

MeasSubframePatternConfigNeigh-r10 ::=	CHOICE {
	release									NULL,
	setup									SEQUENCE {
		measSubframePatternNeigh-r10			MeasSubframePattern-r10,
		measSubframeCellList-r10				MeasSubframeCellList-r10	OPTIONAL	-- Cond always
	}
}

MeasSubframeCellList-r10 ::=	SEQUENCE (SIZE (1..maxCellMeas)) OF PhysCellIdRange

AltTTT-CellsToAddModList-r12 ::=	SEQUENCE (SIZE (1..maxCellMeas)) OF AltTTT-CellsToAddMod-r12

AltTTT-CellsToAddMod-r12 ::=	SEQUENCE {
	cellIndex-r12							INTEGER (1..maxCellMeas),
	physCellIdRange-r12						PhysCellIdRange
}

WhiteCellsToAddModList-r13 ::=			SEQUENCE (SIZE (1..maxCellMeas)) OF WhiteCellsToAddMod-r13

WhiteCellsToAddMod-r13 ::=	SEQUENCE {
	cellIndex-r13							INTEGER (1..maxCellMeas),
	physCellIdRange-r13						PhysCellIdRange
}

MeasRSSI-Config-r13 ::=	CHOICE {
	release								NULL,
	setup								SEQUENCE {
		rmtc-Period-r13					ENUMERATED {ms40, ms80, ms160, ms320, ms640},
		rmtc-SubframeOffset-r13			INTEGER(0..639)					OPTIONAL, 		-- Need ON
		measDuration-r13				ENUMERATED {sym1, sym14, sym28, sym42, sym70}
	}
}

-- ASN1STOP

MeasObjectEUTRA field descriptions
altTTT-CellsToAddModList
List of cells to add/ modify in the cell list for which the alternative time to trigger specified by alternativeTimeToTrigger in reportConfigEUTRA, if configured, applies.
altTTT-CellsToRemoveList
List of cells to remove from the list of cells for alternative time to trigger.
blackCellsToAddModList
List of cells to add/ modify in the black list of cells.
blackCellsToRemoveList
List of cells to remove from the black list of cells.
carrierFreq
Identifies E-UTRA carrier frequency for which this configuration is valid. E-UTRAN does not configure more than one measurement object for the same physical frequency regardless of the E-ARFCN used to indicate this.
cellIndex
Entry index in the cell list. An entry may concern a range of cells, in which case this value applies to the entire range.
cellIndividualOffset
Cell individual offset applicable to a specific cell. Value dB-24 corresponds to -24 dB, dB-22 corresponds to -22 dB and so on.
cellsToAddModList
List of cells to add/ modify in the cell list.
cellsToRemoveList
List of cells to remove from the cell list.
measCycleSCell
The parameter is used only when an SCell is configured on the frequency indicated by the measObject and is in deactivated state, see TS 36.133 [16, 8.3.3]. E-UTRAN configures the parameter whenever an SCell is configured on the frequency indicated by the measObject, but the field may also be signalled when an SCell is not configured. Value sf160 corresponds to 160 sub-frames, sf256 corresponds to 256 sub-frames and so on.
measDS-Config
Parameters applicable to discovery signals measurement on the carrier frequency indicated by carrierFreq.
measDuration
Number of consecutive symbols for which the Physical Layer reports samples of RSSI, see TS 36.214 [48]. Value sym1 corresponds to one symbol, sym14 corresponds to 14 symbols, and so on.
measRSSI-Config
Parameters applicable to RSSI and channel occupancy measurement on the carrier frequency indicated by carrierFreq.
measSubframeCellList
List of cells for which measSubframePatternNeigh is applied.
measSubframePatternNeigh
Time domain measurement resource restriction pattern applicable to neighbour cell RSRP and RSRQ measurements on the carrier frequency indicated by carrierFreq. For cells in measSubframeCellList the UE shall assume that the subframes indicated by measSubframePatternNeigh are non-MBSFN subframes, and have the same special subframe configuration as PCell.
offsetFreq
Offset value applicable to the carrier frequency. Value dB-24 corresponds to -24 dB, dB-22 corresponds to -22 dB and so on.
physCellId
Physical cell identity of a cell in the cell list.
physCellIdRange
Physical cell identity or a range of physical cell identities.
reducedMeasPerformance
If set to TRUE, the EUTRA carrier frequency is configured for reduced measurement performance, otherwise it is configured for normal measurement performance, see TS 36.133 [16].
rmtc-Period
Indicates the RSSI and channel occupancy measurement timing configuration (RMTC) periodicity for this frequency. Value ms40 corresponds to 40 ms periodicity, ms80 corresponds to 80 ms periodicity and so on, see TS 36.214 [48].
rmtc-SubframeOffset
Indicates the RSSI and channel occupancy measurement timing configuration (RMTC) subframe offset for this frequency, see TS 36.214 [48]. For inter-frequency measurements, if this field is not configured, the UE chooses a random starting offset for measDuration.
t312
The value of timer T312. Value ms0 represents 0 ms, ms50 represents 50 ms and so on.
widebandRSRQ-Meas
If this field is set to TRUE, the UE shall, when performing RSRQ measurements, use a wider bandwidth in accordance with TS 36.133 [16].
whiteCellsToAddModList
List of cells to add/modify in the white list of cells.
whiteCellsToRemoveList
List of cells to remove from the white list of cells.

Conditional presence
Explanation
always
The field is mandatory present.
WB-RSRQ
The field is optionally present, need ON, if the measurement bandwidth indicated by allowedMeasBandwidth is 50 resource blocks or larger; otherwise it is not present and the UE shall delete any existing value for this field, if configured.

-	MeasObjectGERAN
The IE MeasObjectGERAN specifies information applicable for inter-RAT GERAN neighbouring frequencies.
MeasObjectGERAN information element
-- ASN1START

MeasObjectGERAN ::=					SEQUENCE {
	carrierFreqs						CarrierFreqsGERAN,
	offsetFreq							Q-OffsetRangeInterRAT		DEFAULT 0,
	ncc-Permitted						BIT STRING(SIZE (8))		DEFAULT '11111111'B,
	cellForWhichToReportCGI				PhysCellIdGERAN				OPTIONAL, 	-- Need ON
	...
}

-- ASN1STOP

MeasObjectGERAN field descriptions
ncc-Permitted
Field encoded as a bit map, where bit N is set to "0" if a BCCH carrier with NCC = N-1 is not permitted for monitoring and set to "1" if a BCCH carrier with NCC = N-1 is permitted for monitoring; N = 1 to 8; bit 1 of the bitmap is the leading bit of the bit string.
carrierFreqs
If E-UTRAN includes cellForWhichToReportCGI, it includes only one GERAN ARFCN value in carrierFreqs.

-	MeasObjectId
The IE MeasObjectId used to identify a measurement object configuration.
MeasObjectId information element
-- ASN1START

MeasObjectId ::=					INTEGER (1..maxObjectId)

-- ASN1STOP

-	MeasObjectToAddModList
The IE MeasObjectToAddModList concerns a list of measurement objects to add or modify
MeasObjectToAddModList information element
-- ASN1START

MeasObjectToAddModList ::=			SEQUENCE (SIZE (1..maxObjectId)) OF MeasObjectToAddMod

MeasObjectToAddModList-v9e0 ::=		SEQUENCE (SIZE (1..maxObjectId)) OF MeasObjectToAddMod-v9e0

MeasObjectToAddMod ::=	SEQUENCE {
	measObjectId						MeasObjectId,
	measObject							CHOICE {
		measObjectEUTRA						MeasObjectEUTRA,
		measObjectUTRA						MeasObjectUTRA,
		measObjectGERAN						MeasObjectGERAN,
		measObjectCDMA2000					MeasObjectCDMA2000,
		...
	}
}

MeasObjectToAddMod-v9e0 ::=	SEQUENCE {
	measObjectEUTRA-v9e0				MeasObjectEUTRA-v9e0		OPTIONAL	-- Cond eutra
}

-- ASN1STOP

Conditional presence
Explanation
eutra
The field is optional present, need OR, if for the corresponding entry in MeasObjectToAddModList field measObject is set to measObjectEUTRA and its sub-field carrierFreq is set to maxEARFCN. Otherwise the field is not present and the UE shall delete any existing value for this field.

-	MeasObjectUTRA
The IE MeasObjectUTRA specifies information applicable for inter-RAT UTRA neighbouring cells.
MeasObjectUTRA information element
-- ASN1START

MeasObjectUTRA ::=					SEQUENCE {
	carrierFreq							ARFCN-ValueUTRA,
	offsetFreq							Q-OffsetRangeInterRAT		DEFAULT 0,
	cellsToRemoveList					CellIndexList				OPTIONAL,			-- Need ON
	cellsToAddModList					CHOICE {
		cellsToAddModListUTRA-FDD			CellsToAddModListUTRA-FDD,
		cellsToAddModListUTRA-TDD			CellsToAddModListUTRA-TDD
	}																OPTIONAL,			-- Need ON
	cellForWhichToReportCGI				CHOICE {
		utra-FDD							PhysCellIdUTRA-FDD,
		utra-TDD							PhysCellIdUTRA-TDD
	}																OPTIONAL, 	-- Need ON
	...,
	[[	csg-allowedReportingCells-v930			CSG-AllowedReportingCells-r9	OPTIONAL		-- Need ON
	]],
	[[	reducedMeasPerformance-r12				BOOLEAN 			OPTIONAL	 	-- Need ON
	]]
}

CellsToAddModListUTRA-FDD ::=		SEQUENCE (SIZE (1..maxCellMeas)) OF CellsToAddModUTRA-FDD 

CellsToAddModUTRA-FDD ::=	SEQUENCE {
	cellIndex							INTEGER (1..maxCellMeas),
	physCellId							PhysCellIdUTRA-FDD
}

CellsToAddModListUTRA-TDD ::=		SEQUENCE (SIZE (1..maxCellMeas)) OF CellsToAddModUTRA-TDD 

CellsToAddModUTRA-TDD ::=	SEQUENCE {
	cellIndex							INTEGER (1..maxCellMeas),
	physCellId							PhysCellIdUTRA-TDD
}

CSG-AllowedReportingCells-r9 ::=		SEQUENCE {
	physCellIdRangeUTRA-FDDList-r9			PhysCellIdRangeUTRA-FDDList-r9	OPTIONAL	-- Need OR
}
-- ASN1STOP

MeasObjectUTRA field descriptions
carrierFreq
Identifies UTRA carrier frequency for which this configuration is valid. E-UTRAN does not configure more than one measurement object for the same physical frequency regardless of the ARFCN used to indicate this.
cellIndex
Entry index in the neighbouring cell list.
cellsToAddModListUTRA-FDD
List of UTRA FDD cells to add/ modify in the neighbouring cell list.
cellsToAddModListUTRA-TDD
List of UTRA TDD cells to add/modify in the neighbouring cell list.
cellsToRemoveList
List of cells to remove from the neighbouring cell list.
csg-allowedReportingCells
One or more ranges of physical cell identities for which UTRA-FDD reporting is allowed.
reducedMeasPerformance
If set to TRUE the UTRA carrier frequency is configured for reduced measurement performance, otherwise it is configured for normal measurement performance, see TS 36.133 [16].

-	MeasResults
The IE MeasResults covers measured results for intra-frequency, inter-frequency and inter- RAT mobility.
MeasResults information element
-- ASN1START

MeasResults ::=						SEQUENCE {
	measId								MeasId,
	measResultPCell					SEQUENCE {
		rsrpResult							RSRP-Range,
		rsrqResult							RSRQ-Range
	},
	measResultNeighCells				CHOICE {
		measResultListEUTRA					MeasResultListEUTRA,
		measResultListUTRA					MeasResultListUTRA,
		measResultListGERAN					MeasResultListGERAN,
		measResultsCDMA2000					MeasResultsCDMA2000,
		...
	}																		OPTIONAL,
	...,
	[[	measResultForECID-r9				MeasResultForECID-r9			OPTIONAL
	]],
	[[	locationInfo-r10					LocationInfo-r10				OPTIONAL,
		measResultServFreqList-r10			MeasResultServFreqList-r10		OPTIONAL
	]],
	[[	measId-v1250						MeasId-v1250					OPTIONAL,
		measResultPCell-v1250				RSRQ-Range-v1250				OPTIONAL,
		measResultCSI-RS-List-r12			MeasResultCSI-RS-List-r12		OPTIONAL
	]],
	[[	measResultForRSSI-r13				MeasResultForRSSI-r13			OPTIONAL,
		measResultServFreqListExt-r13		MeasResultServFreqListExt-r13		OPTIONAL,
		measResultSSTD-r13					MeasResultSSTD-r13				OPTIONAL,
		measResultPCell-v13xy				SEQUENCE {
			rs-sinrResult-r13					RS-SINR-Range-r13
		}																	OPTIONAL,
		ul-PDCP-DelayResultList-r13			UL-PDCP-DelayResultList-r13		OPTIONAL
	]]

}

MeasResultListEUTRA ::=				SEQUENCE (SIZE (1..maxCellReport)) OF MeasResultEUTRA 

MeasResultEUTRA ::=	SEQUENCE {
	physCellId							PhysCellId,
	cgi-Info							SEQUENCE {
		cellGlobalId						CellGlobalIdEUTRA,
		trackingAreaCode					TrackingAreaCode,
		plmn-IdentityList					PLMN-IdentityList2 				OPTIONAL
	}			 												OPTIONAL,
	measResult							SEQUENCE {
		rsrpResult							RSRP-Range						OPTIONAL,
		rsrqResult							RSRQ-Range						OPTIONAL,
		...,
		[[	additionalSI-Info-r9				AdditionalSI-Info-r9				OPTIONAL
		]],
		[[	primaryPLMN-Suitable-r12			ENUMERATED {true}			OPTIONAL,
			measResult-v1250					RSRQ-Range-v1250			OPTIONAL
		]],
		[[	rs-sinrResult-r13					RS-SINR-Range-r13			OPTIONAL
		]]
	}
}

MeasResultServFreqList-r10 ::=	SEQUENCE (SIZE (1..maxServCell-r10)) OF MeasResultServFreq-r10

MeasResultServFreqListExt-r13 ::=	SEQUENCE (SIZE (maxServCell-Plus1..maxServCell-r13)) OF MeasResultServFreq-r13

MeasResultServFreq-r10 ::=			SEQUENCE {
	servFreqId-r10						ServCellIndex-r10,
	measResultSCell-r10					SEQUENCE {
		rsrpResultSCell-r10					RSRP-Range,
		rsrqResultSCell-r10					RSRQ-Range
	}															OPTIONAL,
	measResultBestNeighCell-r10			SEQUENCE {
		physCellId-r10						PhysCellId,
		rsrpResultNCell-r10					RSRP-Range,
		rsrqResultNCell-r10					RSRQ-Range
	}															OPTIONAL,
	...,
	[[	measResultSCell-v1250				RSRQ-Range-v1250	OPTIONAL,
		measResultBestNeighCell-v1250		RSRQ-Range-v1250	OPTIONAL
	]],
	[[	measResultSCell-v13xy				SEQUENCE {
			rs-sinrResult-r13					RS-SINR-Range-r13
		}		OPTIONAL,
		measResultBestNeighCell-v13xy		SEQUENCE {
			rs-sinrResult-r13					RS-SINR-Range-r13
		}		OPTIONAL
	]]
}

MeasResultServFreq-r13 ::=			SEQUENCE {
	servFreqId-r13						ServCellIndexFull-r13,
	measResultSCell-r13					SEQUENCE {
		rsrpResultSCell-r13					RSRP-Range,
		rsrqResultSCell-r13					RSRQ-Range-v13xx,
		rs-sinrResult-r13					RS-SINR-Range-r13	OPTIONAL
	}															OPTIONAL,
	measResultBestNeighCell-r13			SEQUENCE {
		physCellId-r13						PhysCellId,
		rsrpResultNCell-r10					RSRP-Range,
		rsrqResultNCell-r13					RSRQ-Range-v13xx,
		rs-sinrResult-r13					RS-SINR-Range-r13	OPTIONAL
	}															OPTIONAL,
	...
}

MeasResultCSI-RS-List-r12 ::=	SEQUENCE (SIZE (1..maxCellReport)) OF MeasResultCSI-RS-r12

MeasResultCSI-RS-r12 ::=		SEQUENCE {
	measCSI-RS-Id-r12				MeasCSI-RS-Id-r12,
	csi-RSRP-Result-r12				CSI-RSRP-Range-r12,
	...
}

MeasResultListUTRA ::=				SEQUENCE (SIZE (1..maxCellReport)) OF MeasResultUTRA 

MeasResultUTRA ::=	SEQUENCE {
	physCellId							CHOICE {
		fdd									PhysCellIdUTRA-FDD,
		tdd									PhysCellIdUTRA-TDD
	},
	cgi-Info							SEQUENCE {
		cellGlobalId						CellGlobalIdUTRA,
		locationAreaCode					BIT STRING (SIZE (16))			OPTIONAL,
		routingAreaCode						BIT STRING (SIZE (8))			OPTIONAL,
		plmn-IdentityList					PLMN-IdentityList2 				OPTIONAL
	}			 												OPTIONAL,
	measResult							SEQUENCE {
		utra-RSCP							INTEGER (-5..91)				OPTIONAL,
		utra-EcN0							INTEGER (0..49)					OPTIONAL,
		...,
		[[	additionalSI-Info-r9				AdditionalSI-Info-r9				OPTIONAL
		]],
		[[	primaryPLMN-Suitable-r12			ENUMERATED {true}			OPTIONAL
		]]
	}
}

MeasResultListGERAN ::=				SEQUENCE (SIZE (1..maxCellReport)) OF MeasResultGERAN 

MeasResultGERAN ::=	SEQUENCE {
	carrierFreq							CarrierFreqGERAN,
	physCellId							PhysCellIdGERAN,
	cgi-Info							SEQUENCE {
		cellGlobalId						CellGlobalIdGERAN,
		routingAreaCode						BIT STRING (SIZE (8))			OPTIONAL
	}			 															OPTIONAL,
	measResult							SEQUENCE {
		rssi								INTEGER (0..63),
		...
	}
}

MeasResultsCDMA2000 ::=				SEQUENCE {
	preRegistrationStatusHRPD			BOOLEAN,
	measResultListCDMA2000				MeasResultListCDMA2000
}

MeasResultListCDMA2000 ::=			SEQUENCE (SIZE (1..maxCellReport)) OF MeasResultCDMA2000

MeasResultCDMA2000 ::=	SEQUENCE {
	physCellId							PhysCellIdCDMA2000,
	cgi-Info							CellGlobalIdCDMA2000		 		OPTIONAL,
	measResult							SEQUENCE {
		pilotPnPhase						INTEGER	(0..32767)				OPTIONAL,
		pilotStrength						INTEGER (0..63),
		...
	}
}

MeasResultForECID-r9 ::=		SEQUENCE {
	ue-RxTxTimeDiffResult-r9				INTEGER (0..4095),
	currentSFN-r9							BIT STRING (SIZE (10))
}

PLMN-IdentityList2 ::=				SEQUENCE (SIZE (1..5)) OF PLMN-Identity

AdditionalSI-Info-r9 ::=			SEQUENCE {
	csg-MemberStatus-r9				ENUMERATED {member}				OPTIONAL,
	csg-Identity-r9						CSG-Identity						OPTIONAL
}
MeasResultForRSSI-r13 ::=			SEQUENCE {
	rssi-Result-r13							RSSI-Range-r13, 
	channelOccupancy-r13					INTEGER (0..100)
}

UL-PDCP-DelayResultList-r13 ::=		SEQUENCE (SIZE (1..maxQCI-r13)) OF UL-PDCP-DelayResult-r13


UL-PDCP-DelayResult-r13 ::=			SEQUENCE {
	qci-Id-r13							ENUMERATED {qci1, qci2, qci3, qci4, spare4, spare3, spare2, spare1},
	excessDelay-r13						INTEGER (0..31) 
}

-- ASN1STOP

MeasResults field descriptions
channelOccupancy
Indicates the percentage of samples when the RSSI was above the configured channelOccupancyThreshold for the associated reportConfig. 
csg-MemberStatus
Indicates whether or not the UE is a member of the CSG of the neighbour cell.
currentSFN
Indicates the current system frame number when receiving the UE Rx-Tx time difference measurement results from lower layer.
excessDelay
Indicates Excess Queueing Delay Ratio in UL, according to Excess Delay Ratio measurement report mapping table, as defined in TS 36.314 [71, Table 4.2.1.1.1-1]
locationAreaCode
A fixed length code identifying the location area within a PLMN, as defined in TS 23.003 [27].
measId
Identifies the measurement identity for which the reporting is being performed. If the measId-v1250 is included, the measId (i.e. without a suffix) is ignored by eNB.
measResult
Measured result of an E-UTRA cell;
Measured result of a UTRA cell;
Measured result of a GERAN cell or frequency;
Measured result of a CDMA2000 cell;
Measured result of UE Rx-Tx time difference; or
Measured result of UE SFN and subframe timing difference.
measResultCSI-RS-List
Measured results of the CSI-RS resources in discovery signals measurement. 
measResultListCDMA2000
List of measured results for the maximum number of reported best cells for a CDMA2000 measurement identity.
measResultListEUTRA
List of measured results for the maximum number of reported best cells for an E-UTRA measurement identity.
measResultListGERAN
List of measured results for the maximum number of reported best cells or frequencies for a GERAN measurement identity.
measResultListUTRA
List of measured results for the maximum number of reported best cells for a UTRA measurement identity.
measResultPCell
Measured result of the PCell.
measResultsCDMA2000
Contains the CDMA2000 HRPD pre-registration status and the list of CDMA2000 measurements.
MeasResultServFreqList
Measured results of the serving frequencies: the measurement result of each SCell, if any, and of the best neighbouring cell on each serving frequency. 
pilotPnPhase
Indicates the arrival time of a CDMA2000 pilot, measured relative to the UE's time reference in units of PN chips, see C.S0005 [25]. This information is used in either SRVCC handover or enhanced 1xRTT CS fallback procedure to CDMA2000 1xRTT.
pilotStrength
CDMA2000 Pilot Strength, the ratio of pilot power to total power in the signal bandwidth of a CDMA2000 Forward Channel. See C.S0005 [25] for CDMA2000 1xRTT and C.S0024 [26] for CDMA2000 HRPD.
plmn-IdentityList
The list of PLMN Identity read from broadcast information when the multiple PLMN Identities are broadcast.
preRegistrationStatusHRPD
Set to TRUE if the UE is currently pre-registered with CDMA2000 HRPD. Otherwise set to FALSE. This can be ignored by the eNB for CDMA2000 1xRTT.
qci-Id
Indicates QCI value for which excessDelay is provided, according to TS 36.314 [71].
routingAreaCode
The RAC identity read from broadcast information, as defined in TS 23.003 [27].
rsrpResult
Measured RSRP result of an E-UTRA cell.
The rsrpResult is only reported if configured by the eNB.
rsrqResult
Measured RSRQ result of an E-UTRA cell.
The rsrqResult is only reported if configured by the eNB.
rssi
GERAN Carrier RSSI. RXLEV is mapped to a value between 0 and 63, TS 45.008 [28]. When mapping the RXLEV value to the RSSI bit string, the first/leftmost bit of the bit string contains the most significant bit.
rs-sinrResult
Measured RS-SINR result of an E-UTRA cell.
The rs-sinrResult is only reported if configured by the eNB.
ue-RxTxTimeDiffResult
UE Rx-Tx time difference measurement result of the PCell, provided by lower layers. According to UE Rx-Tx time difference report mapping in TS 36.133 [16].

utra-EcN0
According to CPICH_Ec/No in TS 25.133 [29] for FDD. Fourteen spare values. The field is not present for TDD.
utra-RSCP
According to CPICH_RSCP in TS 25.133 [29] for FDD and P-CCPCH_RSCP in TS 25.123 [30] for TDD. Thirty-one spare values.

-	MeasResultSSTD
The IE MeasResultSSTD consists of SFN, radio frame and subframe boundary difference between the PCell and the PSCell as specified in TS 36.214 [48].
MeasResultSSTD information element
-- ASN1START

MeasResultSSTD-r13 ::=						SEQUENCE {
	sfn-OffsetResult-r13						INTEGER (0..1023),
	frameBoundaryOffsetResult-r13				INTEGER (-4..5),
	subframeBoundaryOffsetResult-r13			INTEGER (0..63)
}

-- ASN1STOP

MeasResultSSTD field descriptions
sfn-OffsetResult
Indicates the SFN difference between the PCell and the PSCell as an integer value according to TS 36.214 [48].
frameBoundaryOffsetResult
Indicates the frame boundary difference between the PCell and the PSCell as an integer value according to TS 36.214 [48].
subframeBoundaryOffsetResult
Indicates the subframe boundary difference between the PCell and the PSCell as an integer value according to the mapping table in TS 36.133 [16].

-	MeasScaleFactor

The IE MeasScaleFactor specifies the factor for scaling the measurement performance requirements in TS 36.133 [16].
MeasScaleFactor information element
-- ASN1START

MeasScaleFactor-r12 ::=			ENUMERATED {sf-EUTRA-cf1, sf-EUTRA-cf2}

-- ASN1STOP

NOTE:	If the reducedMeasPerformance is not included in any measObjectEUTRA or measObjectUTRA and the measScaleFactor is included in the measConfig, E-UTRAN can configure any of the values for the measScaleFactor as specified in TS 36.133 [16].
-	QuantityConfig
The IE QuantityConfig specifies the measurement quantities and layer 3 filtering coefficients for E-UTRA and inter-RAT measurements.
QuantityConfig information element
-- ASN1START

QuantityConfig ::=					SEQUENCE {
	quantityConfigEUTRA					QuantityConfigEUTRA					OPTIONAL,	-- Need ON
	quantityConfigUTRA					QuantityConfigUTRA					OPTIONAL,	-- Need ON
	quantityConfigGERAN					QuantityConfigGERAN					OPTIONAL,	-- Need ON
	quantityConfigCDMA2000				QuantityConfigCDMA2000				OPTIONAL,	-- Need ON
	...,
	[[	quantityConfigUTRA-v1020		QuantityConfigUTRA-v1020			OPTIONAL	-- Need ON
	]],
	[[	quantityConfigEUTRA-v1250		QuantityConfigEUTRA-v1250			OPTIONAL	-- Need ON
	]],
	[[	quantityConfigEUTRA-v13xy		QuantityConfigEUTRA-v13xy			OPTIONAL	-- Need ON
	]]
}

QuantityConfigEUTRA ::=				SEQUENCE {
	filterCoefficientRSRP				FilterCoefficient					DEFAULT fc4,
	filterCoefficientRSRQ				FilterCoefficient					DEFAULT fc4
}

QuantityConfigEUTRA-v1250 ::=		SEQUENCE {
	filterCoefficientCSI-RSRP-r12		FilterCoefficient					OPTIONAL		-- Need OR
}

QuantityConfigEUTRA-v13xy ::=		SEQUENCE {
	filterCoefficientRS-SINR-r13		FilterCoefficient					DEFAULT fc4
}

QuantityConfigUTRA ::=				SEQUENCE {
	measQuantityUTRA-FDD				ENUMERATED {cpich-RSCP, cpich-EcN0},
	measQuantityUTRA-TDD				ENUMERATED {pccpch-RSCP},
	filterCoefficient					FilterCoefficient					DEFAULT fc4
}

QuantityConfigUTRA-v1020 ::=		SEQUENCE {
	filterCoefficient2-FDD-r10			FilterCoefficient					DEFAULT fc4
}

QuantityConfigGERAN ::=				SEQUENCE {
	measQuantityGERAN					ENUMERATED {rssi},
	filterCoefficient					FilterCoefficient					DEFAULT fc2
}

QuantityConfigCDMA2000 ::=			SEQUENCE {
	measQuantityCDMA2000				ENUMERATED {pilotStrength, pilotPnPhaseAndPilotStrength}
}

-- ASN1STOP

QuantityConfig field descriptions
filterCoefficient2-FDD
Specifies the filtering coefficient used for the UTRAN FDD measurement quantity, which is not included in measQuantityUTRA-FDD, when reportQuantityUTRA-FDD is present in ReportConfigInterRAT.
filterCoefficientCSI-RSRP
Specifies the filtering coefficient used for CSI-RSRP.
filterCoefficientRSRP
Specifies the filtering coefficient used for RSRP.
filterCoefficientRSRQ
Specifies the filtering coefficient used for RSRQ.
filterCoefficientRS-SINR
Specifies the filtering coefficient used for RS-SINR.
measQuantityCDMA2000
Measurement quantity used for CDMA2000 measurements. pilotPnPhaseAndPilotStrength is only applicable for MeasObjectCDMA2000 of cdma2000-Type = type1XRTT.
measQuantityGERAN
Measurement quantity used for GERAN measurements.
measQuantityUTRA
Measurement quantity used for UTRA measurements.
quantityConfigCDMA2000
Specifies quantity configurations for CDMA2000 measurements.
quantityConfigEUTRA
Specifies filter configurations for E-UTRA measurements.
quantityConfigGERAN
Specifies quantity and filter configurations for GERAN measurements.
quantityConfigUTRA
Specifies quantity and filter configurations for UTRA measurements. Field quantityConfigUTRA-v1020 is applicable only when reportQuantityUTRA-FDD is configured.

-	ReportConfigEUTRA
The IE ReportConfigEUTRA specifies criteria for triggering of an E-UTRA measurement reporting event. The E-UTRA measurement reporting events concerning CRS are labelled AN with N equal to 1, 2 and so on.
Event A1:	Serving becomes better than absolute threshold;
Event A2:	Serving becomes worse than absolute threshold;
Event A3:	Neighbour becomes amount of offset better than PCell/ PSCell;
Event A4:	Neighbour becomes better than absolute threshold;
Event A5:	PCell/ PSCell becomes worse than absolute threshold1 AND Neighbour becomes better than another absolute threshold2.
Event A6:	Neighbour becomes amount of offset better than SCell.
The E-UTRA measurement reporting events concerning CSI-RS are labelled CN with N equal to 1 and 2.
Event C1:	CSI-RS resource becomes better than absolute threshold;
Event C2:	CSI-RS resource becomes amount of offset better than reference CSI-RS resource.
ReportConfigEUTRA information element
-- ASN1START

ReportConfigEUTRA ::=				SEQUENCE {
	triggerType							CHOICE {
		event								SEQUENCE {
			eventId								CHOICE {
				eventA1								SEQUENCE {
					a1-Threshold						ThresholdEUTRA
				},
				eventA2								SEQUENCE {
					a2-Threshold						ThresholdEUTRA
				},
				eventA3								SEQUENCE {
					a3-Offset							INTEGER (-30..30),
					reportOnLeave						BOOLEAN
				},
				eventA4								SEQUENCE {
					a4-Threshold						ThresholdEUTRA
				},
				eventA5								SEQUENCE {
					a5-Threshold1						ThresholdEUTRA,
					a5-Threshold2						ThresholdEUTRA
				},
				...,
				eventA6-r10							SEQUENCE {
					a6-Offset-r10						INTEGER (-30..30),
					a6-ReportOnLeave-r10				BOOLEAN
				},
				eventC1-r12							SEQUENCE {
					c1-Threshold-r12					ThresholdEUTRA-v1250,
					c1-ReportOnLeave-r12				BOOLEAN
				},
				eventC2-r12							SEQUENCE {
					c2-RefCSI-RS-r12					MeasCSI-RS-Id-r12,
					c2-Offset-r12						INTEGER (-30..30),
					c2-ReportOnLeave-r12				BOOLEAN
				}
			},
			hysteresis							Hysteresis,
			timeToTrigger						TimeToTrigger
		},
		periodical								SEQUENCE {
			purpose									ENUMERATED {
														reportStrongestCells, reportCGI}
		}
	},
	triggerQuantity						ENUMERATED {rsrp, rsrq},
	reportQuantity						ENUMERATED {sameAsTriggerQuantity, both},
	maxReportCells						INTEGER (1..maxCellReport),
	reportInterval						ReportInterval,
	reportAmount						ENUMERATED {r1, r2, r4, r8, r16, r32, r64, infinity},
	...,
	[[	si-RequestForHO-r9					ENUMERATED {setup}		OPTIONAL,	-- Cond reportCGI
		ue-RxTxTimeDiffPeriodical-r9		ENUMERATED {setup}		OPTIONAL	-- Need OR
	]],
	[[	includeLocationInfo-r10		 		ENUMERATED {true}		OPTIONAL,	-- Need OR
		reportAddNeighMeas-r10				ENUMERATED {setup}		OPTIONAL	-- Need OR
	]],
	[[	alternativeTimeToTrigger-r12		CHOICE {
			release								NULL,
			setup								TimeToTrigger
		}													OPTIONAL,	-- Need ON
		useT312-r12							BOOLEAN			OPTIONAL,	-- Need ON
		usePSCell-r12						BOOLEAN			OPTIONAL, 	-- Need ON
		aN-Threshold1-v1250					RSRQ-RangeConfig-r12		OPTIONAL, 	-- Need ON
		a5-Threshold2-v1250					RSRQ-RangeConfig-r12		OPTIONAL, 	-- Need ON
		reportStrongestCSI-RSs-r12			BOOLEAN		OPTIONAL,	-- Need ON
		reportCRS-Meas-r12					BOOLEAN		OPTIONAL,	-- Need ON
		triggerQuantityCSI-RS-r12			BOOLEAN			OPTIONAL		-- Need ON
	]],
	[[	reportSSTD-Meas-r13					BOOLEAN			OPTIONAL,		-- Need ON
		triggerQuantity-v13xy			CHOICE {
			release							NULL,
			setup							ENUMERATED {sinr}
		}													OPTIONAL,	-- Need ON
		aN-ThresholdSINR-r13			CHOICE {
			release							NULL,
			setup							SEQUENCE {
				threshold1-r13					ThresholdEUTRA-v13xy		OPTIONAL, 	-- Need ON
				threshold2-r13					ThresholdEUTRA-v13xy		OPTIONAL 	-- Need ON
			}
		}													OPTIONAL,	-- Cond SINR
		reportQuantity-v13xy			CHOICE {
			release							NULL,
			setup							ENUMERATED {rsrpANDsinr, rsrqANDsinr, all}
		}													OPTIONAL,	-- Need ON
		useWhiteCellList-r13				BOOLEAN			OPTIONAL,	-- Need ON
		measRSSI-ReportConfig-r13			MeasRSSI-ReportConfig-r13	OPTIONAL	-- Need OR
	]]
}

RSRQ-RangeConfig-r12 ::=			CHOICE {
	release								NULL,
	setup								RSRQ-Range-v1250
}

ThresholdEUTRA ::=					CHOICE{
	threshold-RSRP						RSRP-Range,
	threshold-RSRQ						RSRQ-Range
}

ThresholdEUTRA-v1250 ::=			CSI-RSRP-Range-r12

ThresholdEUTRA-v13xy ::=			RS-SINR-Range-r13

MeasRSSI-ReportConfig-r13 ::=	SEQUENCE {
	channelOccupancyThreshold-r13			RSSI-Range-r13
}

-- ASN1STOP

ReportConfigEUTRA field descriptions
a3-Offset/ a6-Offset/ c2-Offset
Offset value to be used in EUTRA measurement report triggering condition for event a3/ a6/ c2. The actual value is IE value * 0.5 dB.
alternativeTimeToTrigger
Indicates the time to trigger applicable for cells specified in altTTT-CellsToAddModList of the associated measurement object, if configured
aN-ThresholdM/ cN-ThresholdM
Threshold to be used in EUTRA measurement report triggering condition for event number aN/ cN. If multiple thresholds are defined for event number aN/ cN, the thresholds are differentiated by M.
aN-ThresholdSINR
Threshold to be used in EUTRA measurement report triggering condition for event number aN. If multiple thresholds are defined for event number aN, the thresholds are differentiated by M. When configured, UE ignores aN-ThresholdM. E-UTRAN configures threshold1 only for events A1, A2, A4 and A5 and threshold2 only for event A5.
c1-ReportOnLeave/ c2-ReportOnLeave
Indicates whether or not the UE shall initiate the measurement reporting procedure when the leaving condition is met for a CSI-RS resource in csi-RS-TriggeredList, as specified in 5.5.4.1.
c2-RefCSI-RS
Identity of the CSI-RS resource from the measCSI-RS-ToAddModList of the associated measObject, to be used as the reference CSI-RS resource in EUTRA measurement report triggering condition for event c2.
channelOccupancyThreshold
RSSI threshold which is used for channel occupancy evaluation.
eventId
Choice of E-UTRA event triggered reporting criteria. EUTRAN may set this field to eventC1 or eventC2 only if measDS-Config is configured in the associated measObject with one or more CSI-RS resources. The eventC1 and eventC2 are not applicable for the eventId if RS-SINR is configured as triggerQuantity or reportQuantity.
maxReportCells
Max number of cells, excluding the serving cell, to include in the measurement report concerning CRS, and max number of CSI-RS resources to include in the measurement report concerning CSI-RS.
measRSSI-ReportConfig
If this field is present, the UE shall perform RSSI and channel occupancy measurement reporting.
reportAmount
Number of measurement reports applicable for triggerType event as well as for triggerType periodical. In case purpose is set to reportCGI or reportSSTD-Meas is set to true, only value 1 applies.
reportCRS-Meas
Inidicates that UE shall include rsrp, rsrq together with csi-rsrp in the measurement report, if possible.
reportOnLeave/ a6-ReportOnLeave
Indicates whether or not the UE shall initiate the measurement reporting procedure when the leaving condition is met for a cell in cellsTriggeredList, as specified in 5.5.4.1.
reportQuantity 
The quantities to be included in the measurement report. The value both means that both the rsrp and rsrq quantities are to be included in the measurement report. The value rsrpANDsinr and rsrqANDsinr mean that both rsrp and rs-sinr quantities, and both rsrq and rs-sinr quantities are to be included respectively in the measurement report. The value all means that rsrp, rsrq and rs-sinr are to be included in the measurement report. In case triggerQuantityCSI-RS is included, only value sameAsTriggerQuantity applies.
reportSSTD-Meas
If this field is set to true, the UE shall measure SSTD between the PCell and the PSCell as specified in TS 36.214 [48] and ignore the triggerQuantity, reportQuantity and maxReportCells fields. E-UTRAN only sets this field to true when setting triggerType to periodical and purpose to reportStrongestCells.
reportStrongestCSI-RSs
Indicates that periodical CSI-RS measurement report is performed. EUTRAN configures value TRUE only if measDS-Config is configured in the associated measObject with one or more CSI-RS resources.
si-RequestForHO
The field applies to the reportCGI functionality, and when the field is included, the UE is allowed to use autonomous gaps in acquiring system information from the neighbour cell, applies a different value for T321, and includes different fields in the measurement report.
ThresholdEUTRA
For RSRP: RSRP based threshold for event evaluation. The actual value is IE value - 140 dBm.
For RSRQ: RSRQ based threshold for event evaluation. The actual value is (IE value - 40)/2 dB. 
For RS-SINR: RS-SINR based threshold for event evaluation. The actual value is [FFS] dB.
For CSI-RSRP: CSI-RSRP based threshold for event evaluation. The actual value is IE value - 140 dBm.
EUTRAN configures the same threshold quantity for all the thresholds of an event.
timeToTrigger
Time during which specific criteria for the event needs to be met in order to trigger a measurement report.
triggerQuantity 
The quantity used to evaluate the triggering condition for the event concerning CRS. EUTRAN sets the value according to the quantity of the ThresholdEUTRA for this event. The values rsrp, rsrq and sinr correspond to Reference Signal Received Power (RSRP), Reference Signal Received Quality (RSRQ) and Reference Signal Signal to Noise and Interference Ratio (RS-SINR), see TS 36.214 [48].
triggerQuantityCSI-RS 
The quantity used to evaluate the triggering condition for the event concerning CSI-RS. The value TRUE corresponds to CSI Reference Signal Received Power (CSI-RSRP), see TS 36.214 [48]. E-UTRAN configures value TRUE if and only if the measurement reporting event concerns CSI-RS.
ue-RxTxTimeDiffPeriodical
If this field is present, the UE shall perform UE Rx-Tx time difference measurement reporting and ignore the fields triggerQuantity, reportQuantity and maxReportCells. If the field is present, the only applicable values for the corresponding triggerType and purpose are periodical and reportStrongestCells respectively.
usePSCell
If this field is set to TRUE the UE shall use the PSCell instead of the PCell. E-UTRAN configures value TRUE only TRUE only for events A3 and A5, see 5.5.4.4 and 5.5.4.6.
useT312
If value TRUE is configured, the UE shall use the timer T312 with the value t312 as specified in the corresponding measObject. If the corresponding measObject does not include the timer T312 then the timer T312 is considered as not configured. E-UTRAN configures value TRUE only if triggerType is set to event.
useWhiteCellList
If value TRUE is configured, the UE shall consider cells to be applicable for measurements as specified in 5.5.4.1.

Conditional presence
Explanation
reportCGI
The field is optional, need OR, in case purpose is included and set to reportCGI; otherwise the field is not present and the UE shall delete any existing value for this field.
SINR
The field is mandatory, need ON, if triggerQuantitiy is set to sinr; otherwise it is not present and the UE shall delete any existing value for this field.

-	ReportConfigId
The IE ReportConfigId is used to identify a measurement reporting configuration.
ReportConfigId information element
-- ASN1START

ReportConfigId ::=					INTEGER (1..maxReportConfigId)

-- ASN1STOP

-	ReportConfigInterRAT
The IE ReportConfigInterRAT specifies criteria for triggering of an inter-RAT measurement reporting event. The inter-RAT measurement reporting events are labelled BN with N equal to 1, 2 and so on.
Event B1:	Neighbour becomes better than absolute threshold;
Event B2:	PCell becomes worse than absolute threshold1 AND Neighbour becomes better than another absolute threshold2.
The b1 and b2 event thresholds for CDMA2000 are the CDMA2000 pilot detection thresholds are expressed as an unsigned binary number equal to [-2 x 10 log 10 Ec/Io] in units of 0.5dB, see C.S0005 [25] for details.
ReportConfigInterRAT information element
-- ASN1START

ReportConfigInterRAT ::=			SEQUENCE {
	triggerType							CHOICE {
		event								SEQUENCE {
			eventId								CHOICE {
				eventB1								SEQUENCE {
					b1-Threshold						CHOICE {
						b1-ThresholdUTRA					ThresholdUTRA,
						b1-ThresholdGERAN					ThresholdGERAN,
						b1-ThresholdCDMA2000				ThresholdCDMA2000
					}
				},
				eventB2								SEQUENCE {
					b2-Threshold1						ThresholdEUTRA,
					b2-Threshold2						CHOICE {
						b2-Threshold2UTRA					ThresholdUTRA,
						b2-Threshold2GERAN					ThresholdGERAN,
						b2-Threshold2CDMA2000				ThresholdCDMA2000
					}
				},
				...
			},
			hysteresis						Hysteresis,
			timeToTrigger					TimeToTrigger
		},
		periodical								SEQUENCE {
			purpose									ENUMERATED {
														reportStrongestCells,
														reportStrongestCellsForSON,
														reportCGI}
		}
	},
	maxReportCells						INTEGER (1..maxCellReport),
	reportInterval						ReportInterval,	
	reportAmount						ENUMERATED {r1, r2, r4, r8, r16, r32, r64, infinity},
	...,
	[[	si-RequestForHO-r9					ENUMERATED {setup}		OPTIONAL	-- Cond reportCGI
	]],
	[[	reportQuantityUTRA-FDD-r10			ENUMERATED {both}		OPTIONAL	-- Need OR
	]],
	[[	includeLocationInfo-r11		 		BOOLEAN					OPTIONAL	-- Need ON
	]],
	[[	b2-Threshold1-v1250					CHOICE {
			release								NULL,
			setup								RSRQ-Range-v1250
		}															OPTIONAL 	-- Need ON
	]]
}

ThresholdUTRA ::=					CHOICE{
	utra-RSCP							INTEGER (-5..91),
	utra-EcN0							INTEGER (0..49)
}

ThresholdGERAN ::= 				INTEGER (0..63)

ThresholdCDMA2000 ::= 			INTEGER (0..63)

-- ASN1STOP

ReportConfigInterRAT field descriptions
bN-ThresholdM
Threshold to be used in inter RAT measurement report triggering condition for event number bN. If multiple thresholds are defined for event number bN, the thresholds are differentiated by M.
eventId
Choice of inter-RAT event triggered reporting criteria.
maxReportCells
Max number of cells, excluding the serving cell, to include in the measurement report. In case purpose is set to reportStrongestCellsForSON only value 1 applies.
Purpose
reportStrongestCellsForSON applies only in case reportConfig is linked to a measObject set to measObjectUTRA or measObjectCDMA2000.
reportAmount
Number of measurement reports applicable for triggerType event as well as for triggerType periodical. In case purpose is set to reportCGI or reportStrongestCellsForSON only value 1 applies.
reportQuantityUTRA-FDD
The quantities to be included in the UTRA measurement report. The value both means that both the cpich RSCP and cpich EcN0 quantities are to be included in the measurement report.
si-RequestForHO
The field applies to the reportCGI functionality, and when the field is included, the UE is allowed to use autonomous gaps in acquiring system information from the neighbour cell, applies a different value for T321, and includes different fields in the measurement report.
ThresholdGERAN
The actual value is IE value - 110 dBm.
ThresholdUTRA
utra-RSCP corresponds to CPICH_RSCP in TS 25.133 [29] for FDD and P-CCPCH_RSCP in TS 25.123 [30] for TDD. utra-EcN0 corresponds to CPICH_Ec/No in TS 25.133 [29] for FDD, and is not applicable for TDD.
For utra-RSCP: The actual value is IE value - 115 dBm.
For utra-EcN0: The actual value is (IE value - 49)/2 dB.
timeToTrigger
Time during which specific criteria for the event needs to be met in order to trigger a measurement report.

Conditional presence
Explanation
reportCGI
The field is optional, need OR, in case purpose is included and set to reportCGI; otherwise the field is not present and the UE shall delete any existing value for this field.

-	ReportConfigToAddModList
The IE ReportConfigToAddModList concerns a list of reporting configurations to add or modify
ReportConfigToAddModList information element
-- ASN1START

ReportConfigToAddModList ::=		SEQUENCE (SIZE (1..maxReportConfigId)) OF ReportConfigToAddMod

ReportConfigToAddMod ::=	SEQUENCE {
	reportConfigId						ReportConfigId,
	reportConfig						CHOICE {
		reportConfigEUTRA					ReportConfigEUTRA,
		reportConfigInterRAT				ReportConfigInterRAT
	}
}


-- ASN1STOP

-	ReportInterval
The ReportInterval indicates the interval between periodical reports. The ReportInterval is applicable if the UE performs periodical reporting (i.e. when reportAmount exceeds 1), for triggerType event as well as for triggerType periodical. Value ms120 corresponds with 120 ms, ms240 corresponds with 240 ms and so on, while value min1 corresponds with 1 min, min6 corresponds with 6 min and so on.
ReportInterval information element
-- ASN1START

ReportInterval ::=					ENUMERATED {
										ms120, ms240, ms480, ms640, ms1024, ms2048, ms5120, ms10240,
										min1, min6, min12, min30, min60, spare3, spare2, spare1}

-- ASN1STOP

-	RSRP-Range
The IE RSRP-Range specifies the value range used in RSRP measurements and thresholds. Integer value for RSRP measurements according to mapping table in TS 36.133 [16].
RSRP-Range information element
-- ASN1START

RSRP-Range ::=						INTEGER(0..97)

RSRP-RangeSL-r12 ::=				INTEGER(0..13)

RSRP-RangeSL2-r12 ::=				INTEGER(0..7)

RSRP-RangeSL3-r12 ::=				INTEGER(0..11)

-- ASN1STOP

RSRP-Range field descriptions
RSRP-RangeSL
Value 0 corresponds to -infinity, value 1 to -115dBm, value 2 to -110dBm, and so on (i.e. in steps of 5dBm) until value 12, which corresponds to -60dBm, while value 13 corresponds to +infinity.
RSRP-RangeSL2
Value 0 corresponds to -infinity, value 1 to -110dBm, value 2 to -100dBm, and so on (i.e. in steps of 10dBm) until value 6, which corresponds to -60dBm, while value 7 corresponds to +infinity.
RSRP-RangeSL3
Value 0 corresponds to -110dBm, value 1 to -105dBm, value 2 to -100dBm, and so on (i.e. in steps of 5dBm) until value 10, which corresponds to -60dBm, while value 11 corresponds to +infinity.

-	RSRQ-Range
The IE RSRQ-Range specifies the value range used in RSRQ measurements and thresholds. Integer value for RSRQ measurements is according to mapping table in TS 36.133 [16]. A given field using RSRQ-Range-v1250 shall only be signalled if the corresponding original field (using RSRQ-Range i.e. without suffix) is set to value 0 or 34. Only a UE indicating support of extendedRSRQ-LowerRange-r12 or rsrq-OnAllSymbols-r12 may report RSRQ-Range-v1250, and this may be done without explicit configuration from the E-UTRAN. If received, the UE shall use the value indicated by the RSRQ-Range-v1250 and ignore the value signalled by RSRQ-Range (without the suffix).

RSRQ-Range information element
-- ASN1START

RSRQ-Range ::=						INTEGER(0..34)

RSRQ-Range-v1250 ::=				INTEGER(-30..46)

RSRQ-Range-v13xx ::=				INTEGER(-30..46)

-- ASN1STOP

-	RSRQ-Type
The IE RSRQ-Type specifies the RSRQ value type used in RSRQ measurements, see TS 36.214 [48].
RSRQ-Type information element
-- ASN1START

RSRQ-Type-r12 ::=					SEQUENCE {
	allSymbols-r12							BOOLEAN,
	wideBand-r12							BOOLEAN
}

-- ASN1STOP

RSRQ-Type field descriptions
allSymbols
Value TRUE indicates use of all OFDM symbols when performing RSRQ measurements.
wideBand
Value TRUE indicates use of a wider bandwidth when performing RSRQ measurements.

-	RS-SINR-Range
The IE RS-SINR-Range specifies the value range used in RS-SINR measurements and thresholds. Integer value for RS-SINR measurements is according to mapping table in TS 36.133 [16].
RS-SINR-Range information element
-- ASN1START

RS-SINR-Range-r13 ::=						INTEGER(0..127)

-- ASN1STOP

-	RSSI-Range-r13
The IE RSSI-Range specifies the value range used in RSSI measurements and thresholds. Integer value for RSSI measurements is according to mapping table in TS 36.133 [16].
RSSI-Range information element
-- ASN1START

RSSI-Range-r13 ::=						INTEGER(0..76)

-- ASN1STOP


-	TimeToTrigger
The IE TimeToTrigger specifies the value range used for time to trigger parameter, which concerns the time during which specific criteria for the event needs to be met in order to trigger a measurement report. Value ms0 corresponds to 0 ms, ms40 corresponds to 40 ms, and so on.
TimeToTrigger information element
-- ASN1START

TimeToTrigger ::=					ENUMERATED {
										ms0, ms40, ms64, ms80, ms100, ms128, ms160, ms256,
										ms320, ms480, ms512, ms640, ms1024, ms1280, ms2560,
										ms5120}

-- ASN1STOP

-	UL-DelayConfig
The IE UL-DelayConfig IE specifies the configuration of the UL PDCP Packet Delay per QCI measurement specified in TS36.314 [71].
UL-DelayConfig information element
-- ASN1START

UL-DelayConfig-r13 ::=					CHOICE {
		release								NULL,
		setup								SEQUENCE {
			delayThreshold-r13							ENUMERATED {
												ms30, ms40, ms50, ms60, ms70, ms80, 
												ms90,ms100, ms150, ms300, ms500, ms750, spare4,												spare3, spare2, spare1},
			delayReportInterval-r13						ENUMERATED {
												ms1024, ms2048, ms5120, ms10240}
		}
}

-- ASN1STOP

UL-DelayConfig field descriptions
delayReportInterval
Indicates the periodicity for performing and reporting of UL PDCP Packet Delay per QCI measurement specified in TS 36.314 [71]. Value in milliseconds. Value ms1024 means 1024 ms and so on.
delayThreshold
Indicates the delay threshold value used by UE to provide results of UL PDCP Packet Delay per QCI measurement as specified in TS 36.314 [71]. Value in milliseconds. Value ms30 means 30 ms and so on.

6.3.6	Other information elements
-	AbsoluteTimeInfo
The IE AbsoluteTimeInfo indicates an absolute time in a format YY-MM-DD HH:MM:SS and using BCD encoding. The first/ leftmost bit of the bit string contains the most significant bit of the most significant digit of the year and so on.
AbsoluteTimeInfo information element
-- ASN1START

AbsoluteTimeInfo-r10 ::=				BIT STRING (SIZE (48))

-- ASN1STOP

-	AreaConfiguration
The AreaConfiguration indicates area for which UE is requested to perform measurement logging. If not configured, measurement logging is not restricted to specific cells or tracking areas but applies as long as the RPLMN is contained in plmn-IdentityList stored in VarLogMeasReport.
AreaConfiguration information element
-- ASN1START

AreaConfiguration-r10 ::=	CHOICE {
	cellGlobalIdList-r10			CellGlobalIdList-r10,
	trackingAreaCodeList-r10		TrackingAreaCodeList-r10
}

AreaConfiguration-v1130 ::=		SEQUENCE {
	trackingAreaCodeList-v1130		TrackingAreaCodeList-v1130
}

CellGlobalIdList-r10 ::=				SEQUENCE (SIZE (1..32)) OF CellGlobalIdEUTRA

TrackingAreaCodeList-r10 ::=			SEQUENCE (SIZE (1..8)) OF TrackingAreaCode

TrackingAreaCodeList-v1130 ::=	SEQUENCE {
	plmn-Identity-perTAC-List-r11			SEQUENCE (SIZE (1..8)) OF PLMN-Identity
}

-- ASN1STOP

AreaConfiguration field descriptions
plmn-Identity-perTAC-List
Includes the PLMN identity for each of the TA codes included in trackingAreaCodeList. The PLMN identity listed first in plmn-Identity-perTAC-List corresponds with the TA code listed first in trackingAreaCodeList and so on.

-	C-RNTI
The IE C-RNTI identifies a UE having a RRC connection within a cell.
C-RNTI information element
-- ASN1START

C-RNTI ::=							BIT STRING (SIZE (16))

-- ASN1STOP

-	DedicatedInfoCDMA2000
The DedicatedInfoCDMA2000 is used to transfer UE specific CDMA2000 information between the network and the UE. The RRC layer is transparent for this information.
DedicatedInfoCDMA2000 information element
-- ASN1START

DedicatedInfoCDMA2000 ::=				OCTET STRING

-- ASN1STOP

-	DedicatedInfoNAS
The IE DedicatedInfoNAS is used to transfer UE specific NAS layer information between the network and the UE. The RRC layer is transparent for this information.
DedicatedInfoNAS information element
-- ASN1START

DedicatedInfoNAS ::=		OCTET STRING

-- ASN1STOP

-	FilterCoefficient
The IE FilterCoefficient specifies the measurement filtering coefficient. Value fc0 corresponds to k = 0, fc1 corresponds to k = 1, and so on.
FilterCoefficient information element
-- ASN1START

FilterCoefficient ::=					ENUMERATED {
											fc0, fc1, fc2, fc3, fc4, fc5,
											fc6, fc7, fc8, fc9, fc11, fc13, 
											fc15, fc17, fc19, spare1, ...}

-- ASN1STOP

-	LoggingDuration
The LoggingDuration indicates the duration for which UE is requested to perform measurement logging. Value min10 corresponds to 10 minutes, value min20 corresponds to 20 minutes and so on.
LoggingDuration information element
-- ASN1START

LoggingDuration-r10 ::=			ENUMERATED {
									min10, min20, min40, min60, min90, min120, spare2, spare1}

-- ASN1STOP

-	LoggingInterval
The LoggingInterval indicates the periodicity for logging measurement results. Value ms1280 corresponds to 1.28s, value ms2560 corresponds to 2.56s and so on.
LoggingInterval information element
-- ASN1START

LoggingInterval-r10 ::=			ENUMERATED {
									ms1280, ms2560, ms5120, ms10240, ms20480,
									ms30720, ms40960, ms61440}

-- ASN1STOP

-	MeasSubframePattern
The IE MeasSubframePattern is used to specify a subframe pattern. The first/leftmost bit corresponds to the subframe #0 of the radio frame satisfying SFN mod x = 0, where SFN is that of PCell and x is the size of the bit string divided by 10. "1" denotes that the corresponding subframe is used.
MeasSubframePattern information element
-- ASN1START

MeasSubframePattern-r10 ::= CHOICE {
	subframePatternFDD-r10				BIT STRING (SIZE (40)),
	subframePatternTDD-r10				CHOICE {
		subframeConfig1-5-r10					BIT STRING (SIZE (20)),
		subframeConfig0-r10						BIT STRING (SIZE (70)),
		subframeConfig6-r10						BIT STRING (SIZE (60)),
		...
	},
	...
}

-- ASN1STOP

-	MMEC
The IE MMEC identifies an MME within the scope of an MME Group within a PLMN, see TS 23.003 [27]. 
MMEC information element
-- ASN1START

MMEC ::=							BIT STRING (SIZE (8))

-- ASN1STOP


-	NeighCellConfig
The IE NeighCellConfig is used to provide the information related to MBSFN and TDD UL/DL configuration of neighbour cells.
NeighCellConfig information element
-- ASN1START

NeighCellConfig ::=			BIT STRING (SIZE (2))

-- ASN1STOP

NeighCellConfig field descriptions
neighCellConfig
Provides information related to MBSFN and TDD UL/DL configuration of neighbour cells of this frequency
00: Not all neighbour cells have the same MBSFN subframe allocation as the serving cell on this frequency, if configured, and as the PCell otherwise
10: The MBSFN subframe allocations of all neighbour cells are identical to or subsets of that in the serving cell on this frequency, if configured, and of that in the PCell otherwise
01: No MBSFN subframes are present in all neighbour cells
11: Different UL/DL allocation in neighbouring cells for TDD compared to the serving cell on this frequency, if configured, and compared to the PCell otherwise
For TDD, 00, 10 and 01 are only used for same UL/DL allocation in neighbouring cells compared to the serving cell on this frequency, if configured, and compared to the PCell otherwise.

-	OtherConfig
The IE OtherConfig contains configuration related to other configuration
OtherConfig information element
-- ASN1START

OtherConfig-r9 ::= SEQUENCE	{
	reportProximityConfig-r9			ReportProximityConfig-r9		OPTIONAL,	-- Need ON
	...,
	[[	idc-Config-r11					IDC-Config-r11					OPTIONAL,	-- Need ON
		powerPrefIndicationConfig-r11	PowerPrefIndicationConfig-r11	OPTIONAL,	-- Need ON
		obtainLocationConfig-r11		ObtainLocationConfig-r11		OPTIONAL	-- Need ON
	]]
}

IDC-Config-r11 ::= 				SEQUENCE {
	idc-Indication-r11					ENUMERATED {setup}		OPTIONAL,		-- Need OR
	autonomousDenialParameters-r11		SEQUENCE {
			autonomousDenialSubframes-r11			ENUMERATED {n2, n5, n10, n15,
														n20, n30, spare2, spare1},
			autonomousDenialValidity-r11			ENUMERATED {
														sf200, sf500, sf1000, sf2000, 
														spare4, spare3, spare2, spare1}
	}		OPTIONAL, 		-- Need OR
	...,
	[[	idc-Indication-UL-CA-r11		ENUMERATED {setup}		OPTIONAL		-- Cond idc-Ind
	]]
}

ObtainLocationConfig-r11 ::= SEQUENCE {
	obtainLocation-r11				ENUMERATED {setup}				OPTIONAL		-- Need OR
}

PowerPrefIndicationConfig-r11 ::= CHOICE{
	release					NULL,
	setup					SEQUENCE{
		powerPrefIndicationTimer-r11		ENUMERATED {s0, s0dot5, s1, s2, s5, s10, s20, 
											s30, s60, s90, s120, s300, s600, spare3, 
											spare2, spare1}
	}
}

ReportProximityConfig-r9 ::= SEQUENCE {
	proximityIndicationEUTRA-r9		ENUMERATED {enabled}			OPTIONAL,		-- Need OR
	proximityIndicationUTRA-r9		ENUMERATED {enabled}			OPTIONAL		-- Need OR
}

-- ASN1STOP

OtherConfig field descriptions
autonomousDenialSubframes
Indicates the maximum number of the UL subframes for which the UE is allowed to deny any UL transmission. Value n2 corresponds to 2 subframes, n5 to 5 subframes and so on. E-UTRAN does not configure autonomous denial for frequencies on which SCG cells are configured.
autonomousDenialValidity
Indicates the validity period over which the UL autonomous denial subframes shall be counted. Value sf200 corresponds to 200 subframes, sf500 corresponds to 500 subframes and so on.
idc-Indication
The field is used to indicate whether the UE is configured to initiate transmission of the InDeviceCoexIndication message to the network.
idc-Indication-UL-CA
The field is used to indicate whether the UE is configured to provide IDC indications for UL CA using the InDeviceCoexIndication message.
obtainLocation
Requests the UE to attempt to have detailed location information available using GNSS. E-UTRAN configures the field only if includeLocationInfo is configured for one or more measurements.
powerPrefIndicationTimer
Prohibit timer for Power Preference Indication reporting. Value in seconds. Value s0 means prohibit timer is set to 0 second or not set, value s0dot5 means prohibit timer is set to 0.5 second, value s1 means prohibit timer is set to 1 second and so on.
reportProximityConfig
Indicates, for each of the applicable RATs (EUTRA, UTRA), whether or not proximity indication is enabled for CSG member cell(s) of the concerned RAT. Note.

NOTE:	Enabling/ disabling of proximity indication includes enabling/ disabling of the related functionality e.g. autonomous search in connected mode.
Conditional presence
Explanation
idc-Ind
The field is optionally present if idc-Indication is present, need OR. Otherwise the field is not present.

-	RAND-CDMA2000 (1xRTT)
The RAND-CDMA2000 concerns a random value, generated by the eNB, to be passed to the CDMA2000 upper layers.
RAND-CDMA2000 information element
-- ASN1START

RAND-CDMA2000 ::=						BIT STRING (SIZE (32))

-- ASN1STOP

-	RAT-Type
The IE RAT-Type is used to indicate the radio access technology (RAT), including E-UTRA, of the requested/ transferred UE capabilities.
RAT-Type information element
-- ASN1START

RAT-Type ::=						ENUMERATED {
										eutra, utra, geran-cs, geran-ps, cdma2000-1XRTT,
										spare3, spare2, spare1, ...}

-- ASN1STOP

-	RRC-TransactionIdentifier
The IE RRC-TransactionIdentifier is used, together with the message type, for the identification of an RRC procedure (transaction).
RRC-TransactionIdentifier information element
-- ASN1START

RRC-TransactionIdentifier ::=		INTEGER (0..3)

-- ASN1STOP

-	S-TMSI
The IE S-TMSI contains an S-Temporary Mobile Subscriber Identity, a temporary UE identity provided by the EPC which uniquely identifies the UE within the tracking area, see TS 23.003 [27].
S-TMSI information element
-- ASN1START

S-TMSI ::=							SEQUENCE {
	mmec								MMEC,
	m-TMSI								BIT STRING (SIZE (32))
}

-- ASN1STOP

S-TMSI field descriptions
m-TMSI
The first/leftmost bit of the bit string contains the most significant bit of the M-TMSI.

-	TraceReference
The TraceReference contains parameter Trace Reference as defined in TS 32.422 [58].
TraceReference information element
-- ASN1START

TraceReference-r10 ::=			SEQUENCE {
	plmn-Identity-r10				PLMN-Identity,
	traceId-r10						OCTET STRING (SIZE (3))
}

-- ASN1STOP

-	UE-CapabilityRAT-ContainerList
The IE UE-CapabilityRAT-ContainerList contains list of containers, one for each RAT for which UE capabilities are transferred, if any.
UE-CapabilityRAT-ContainerList information element
-- ASN1START

UE-CapabilityRAT-ContainerList ::=SEQUENCE (SIZE (0..maxRAT-Capabilities)) OF UE-CapabilityRAT-Container

UE-CapabilityRAT-Container ::= SEQUENCE {
	rat-Type							RAT-Type,
	ueCapabilityRAT-Container			OCTET STRING
}

-- ASN1STOP

UECapabilityRAT-ContainerList field descriptions
ueCapabilityRAT-Container
Container for the UE capabilities of the indicated RAT. The encoding is defined in the specification of each RAT:
For E-UTRA: the encoding of UE capabilities is defined in IE UE-EUTRA-Capability.
For UTRA: the octet string contains the INTER RAT HANDOVER INFO message defined in TS 25.331 [19].
For GERAN CS: the octet string contains the concatenated string of the Mobile Station Classmark 2 and Mobile Station Classmark 3. The first 5 octets correspond to Mobile Station Classmark 2 and the following octets correspond to Mobile Station Classmark 3. The Mobile Station Classmark 2 is formatted as 'TLV' and is coded in the same way as the Mobile Station Classmark 2 information element in TS 24.008 [49]. The first octet is the Mobile station classmark 2 IEI and its value shall be set to 33H. The second octet is the Length of mobile station classmark 2 and its value shall be set to 3. The octet 3 contains the first octet of the value part of the Mobile Station Classmark 2 information element, the octet 4 contains the second octet of the value part of the Mobile Station Classmark 2 information element and so on. For each of these octets, the first/ leftmost/ most significant bit of the octet contains b8 of the corresponding octet of the Mobile Station Classmark 2. The Mobile Station Classmark 3 is formatted as 'V' and is coded in the same way as the value part in the Mobile station classmark 3 information element in TS 24.008 [49]. The sixth octet of this octet string contains octet 1 of the value part of Mobile station classmark 3, the seventh of octet of this octet string contains octet 2 of the value part of Mobile station classmark 3 and so on. Note.
For GERAN PS: the encoding of UE capabilities is formatted as 'V' and is coded in the same way as the value part in the MS Radio Access Capability information element in TS 24.008 [49].
For CDMA2000-1XRTT: the octet string contains the A21 Mobile Subscription Information and the encoding of this is defined in A.S0008 [33]. The A21 Mobile Subscription Information contains the supported CDMA2000 1xRTT band class and band sub-class information.
NOTE:	The value part is specified by means of CSN.1, which encoding results in a bit string, to which final padding may be appended up to the next octet boundary TS 24.008 [49]. The first/ leftmost bit of the CSN.1 bit string is placed in the first/ leftmost/ most significant bit of the first octet. This continues until the last bit of the CSN.1 bit string, which is placed in the last/ rightmost/ least significant bit of the last octet.
-	UE-EUTRA-Capability
The IE UE-EUTRA-Capability is used to convey the E-UTRA UE Radio Access Capability Parameters, see TS 36.306 [5], and the Feature Group Indicators for mandatory features (defined in Annexes B.1 and C.1) to the network. The IE UE-EUTRA-Capability is transferred in E-UTRA or in another RAT.
UE-EUTRA-Capability information element
-- ASN1START

UE-EUTRA-Capability ::=			SEQUENCE {
	accessStratumRelease				AccessStratumRelease,
	ue-Category							INTEGER (1..5),
	pdcp-Parameters						PDCP-Parameters,
	phyLayerParameters					PhyLayerParameters,
	rf-Parameters						RF-Parameters,
	measParameters						MeasParameters,
	featureGroupIndicators				BIT STRING (SIZE (32))				OPTIONAL,
	interRAT-Parameters				SEQUENCE {
		utraFDD								IRAT-ParametersUTRA-FDD				OPTIONAL,
		utraTDD128							IRAT-ParametersUTRA-TDD128				OPTIONAL,
		utraTDD384							IRAT-ParametersUTRA-TDD384				OPTIONAL,
		utraTDD768							IRAT-ParametersUTRA-TDD768				OPTIONAL,
		geran								IRAT-ParametersGERAN					OPTIONAL,
		cdma2000-HRPD						IRAT-ParametersCDMA2000-HRPD			OPTIONAL,
		cdma2000-1xRTT						IRAT-ParametersCDMA2000-1XRTT			OPTIONAL
	},
	nonCriticalExtension				UE-EUTRA-Capability-v920-IEs		OPTIONAL
}

-- Late non critical extensions
UE-EUTRA-Capability-v9a0-IEs ::=	SEQUENCE {
	featureGroupIndRel9Add-r9			BIT STRING (SIZE (32))				OPTIONAL,
	fdd-Add-UE-EUTRA-Capabilities-r9	UE-EUTRA-CapabilityAddXDD-Mode-r9	OPTIONAL,
	tdd-Add-UE-EUTRA-Capabilities-r9	UE-EUTRA-CapabilityAddXDD-Mode-r9	OPTIONAL,
	nonCriticalExtension				UE-EUTRA-Capability-v9c0-IEs		OPTIONAL
}

UE-EUTRA-Capability-v9c0-IEs ::=		SEQUENCE {
	interRAT-ParametersUTRA-v9c0		IRAT-ParametersUTRA-v9c0		OPTIONAL,
	nonCriticalExtension				UE-EUTRA-Capability-v9d0-IEs	OPTIONAL
}

UE-EUTRA-Capability-v9d0-IEs ::=		SEQUENCE {
	phyLayerParameters-v9d0				PhyLayerParameters-v9d0			OPTIONAL,
	nonCriticalExtension				UE-EUTRA-Capability-v9e0-IEs	OPTIONAL
}

UE-EUTRA-Capability-v9e0-IEs ::=	SEQUENCE {
	rf-Parameters-v9e0					RF-Parameters-v9e0						OPTIONAL,
	nonCriticalExtension				UE-EUTRA-Capability-v9h0-IEs			OPTIONAL
}

UE-EUTRA-Capability-v9h0-IEs ::=	SEQUENCE {
	interRAT-ParametersUTRA-v9h0		IRAT-ParametersUTRA-v9h0			OPTIONAL,
	-- Following field is only to be used for late REL-9 extensions
	lateNonCriticalExtension			OCTET STRING							OPTIONAL,
	nonCriticalExtension				UE-EUTRA-Capability-v10c0-IEs			OPTIONAL
}

UE-EUTRA-Capability-v10c0-IEs ::=	SEQUENCE {
	otdoa-PositioningCapabilities-r10	OTDOA-PositioningCapabilities-r10		OPTIONAL,
	nonCriticalExtension				UE-EUTRA-Capability-v10f0-IEs			OPTIONAL
}

UE-EUTRA-Capability-v10f0-IEs ::=	SEQUENCE {
	rf-Parameters-v10f0					RF-Parameters-v10f0						OPTIONAL,
	nonCriticalExtension				UE-EUTRA-Capability-v10i0-IEs			OPTIONAL
}

UE-EUTRA-Capability-v10i0-IEs ::=	SEQUENCE {
	rf-Parameters-v10i0					RF-Parameters-v10i0						OPTIONAL,
	-- Following field is only to be used for late REL-10 extensions
	lateNonCriticalExtension			OCTET STRING (CONTAINING UE-EUTRA-Capability-v10j0-IEs)	OPTIONAL,
	nonCriticalExtension				UE-EUTRA-Capability-v11d0-IEs			OPTIONAL
}

UE-EUTRA-Capability-v10j0-IEs ::=	SEQUENCE {
	rf-Parameters-v10j0					RF-Parameters-v10j0						OPTIONAL,
	nonCriticalExtension				SEQUENCE {}								OPTIONAL
}

UE-EUTRA-Capability-v11d0-IEs ::=	SEQUENCE {
	rf-Parameters-v11d0					RF-Parameters-v11d0						OPTIONAL,
	otherParameters-v11d0				Other-Parameters-v11d0					OPTIONAL,
	-- Following field is only to be used for late REL-11 extensions
	nonCriticalExtension				SEQUENCE {}								OPTIONAL
}

-- Regular non critical extensions
UE-EUTRA-Capability-v920-IEs ::=		SEQUENCE {
	phyLayerParameters-v920				PhyLayerParameters-v920,
	interRAT-ParametersGERAN-v920			IRAT-ParametersGERAN-v920,
	interRAT-ParametersUTRA-v920			IRAT-ParametersUTRA-v920			OPTIONAL,
	interRAT-ParametersCDMA2000-v920		IRAT-ParametersCDMA2000-1XRTT-v920	OPTIONAL,
	deviceType-r9							ENUMERATED {noBenFromBatConsumpOpt}	OPTIONAL,
	csg-ProximityIndicationParameters-r9	CSG-ProximityIndicationParameters-r9,
	neighCellSI-AcquisitionParameters-r9	NeighCellSI-AcquisitionParameters-r9,
	son-Parameters-r9						SON-Parameters-r9,
	nonCriticalExtension					UE-EUTRA-Capability-v940-IEs		OPTIONAL
}

UE-EUTRA-Capability-v940-IEs ::=	SEQUENCE {
	lateNonCriticalExtension			OCTET STRING (CONTAINING UE-EUTRA-Capability-v9a0-IEs)
																			OPTIONAL,
	nonCriticalExtension				UE-EUTRA-Capability-v1020-IEs		OPTIONAL
}

UE-EUTRA-Capability-v1020-IEs ::=	SEQUENCE {
	ue-Category-v1020					INTEGER (6..8)							OPTIONAL,
	phyLayerParameters-v1020			PhyLayerParameters-v1020				OPTIONAL,
	rf-Parameters-v1020					RF-Parameters-v1020						OPTIONAL,
	measParameters-v1020				MeasParameters-v1020					OPTIONAL,
	featureGroupIndRel10-r10			BIT STRING (SIZE (32))					OPTIONAL,
	interRAT-ParametersCDMA2000-v1020	IRAT-ParametersCDMA2000-1XRTT-v1020		OPTIONAL,
	ue-BasedNetwPerfMeasParameters-r10	UE-BasedNetwPerfMeasParameters-r10		OPTIONAL,
	interRAT-ParametersUTRA-TDD-v1020	IRAT-ParametersUTRA-TDD-v1020			OPTIONAL,
	nonCriticalExtension				UE-EUTRA-Capability-v1060-IEs			OPTIONAL
}

UE-EUTRA-Capability-v1060-IEs ::=	SEQUENCE {
	fdd-Add-UE-EUTRA-Capabilities-v1060	UE-EUTRA-CapabilityAddXDD-Mode-v1060	OPTIONAL,
	tdd-Add-UE-EUTRA-Capabilities-v1060	UE-EUTRA-CapabilityAddXDD-Mode-v1060	OPTIONAL,
	rf-Parameters-v1060					RF-Parameters-v1060						OPTIONAL,
	nonCriticalExtension				UE-EUTRA-Capability-v1090-IEs			OPTIONAL
}

UE-EUTRA-Capability-v1090-IEs ::=	SEQUENCE {
	rf-Parameters-v1090					RF-Parameters-v1090						OPTIONAL,
	nonCriticalExtension				UE-EUTRA-Capability-v1130-IEs			OPTIONAL
}

UE-EUTRA-Capability-v1130-IEs ::=	SEQUENCE {
	pdcp-Parameters-v1130				PDCP-Parameters-v1130,
	phyLayerParameters-v1130			PhyLayerParameters-v1130				OPTIONAL,
	rf-Parameters-v1130					RF-Parameters-v1130,
	measParameters-v1130				MeasParameters-v1130,
	interRAT-ParametersCDMA2000-v1130	IRAT-ParametersCDMA2000-v1130,
	otherParameters-r11					Other-Parameters-r11,
	fdd-Add-UE-EUTRA-Capabilities-v1130	UE-EUTRA-CapabilityAddXDD-Mode-v1130	OPTIONAL,
	tdd-Add-UE-EUTRA-Capabilities-v1130	UE-EUTRA-CapabilityAddXDD-Mode-v1130	OPTIONAL,
	nonCriticalExtension				UE-EUTRA-Capability-v1170-IEs			OPTIONAL
}

UE-EUTRA-Capability-v1170-IEs ::=	SEQUENCE {
	phyLayerParameters-v1170			PhyLayerParameters-v1170				OPTIONAL,
	ue-Category-v1170					INTEGER (9..10)							OPTIONAL,
	nonCriticalExtension				UE-EUTRA-Capability-v1180-IEs			OPTIONAL
}

UE-EUTRA-Capability-v1180-IEs ::=	SEQUENCE {
	rf-Parameters-v1180					RF-Parameters-v1180						OPTIONAL,
	mbms-Parameters-r11					MBMS-Parameters-r11						OPTIONAL,
	fdd-Add-UE-EUTRA-Capabilities-v1180	UE-EUTRA-CapabilityAddXDD-Mode-v1180	OPTIONAL,
	tdd-Add-UE-EUTRA-Capabilities-v1180	UE-EUTRA-CapabilityAddXDD-Mode-v1180	OPTIONAL,
	nonCriticalExtension				UE-EUTRA-Capability-v11a0-IEs			OPTIONAL
}

UE-EUTRA-Capability-v11a0-IEs ::=	SEQUENCE {
	ue-Category-v11a0					INTEGER (11..12)						OPTIONAL,
	measParameters-v11a0				MeasParameters-v11a0					OPTIONAL,
	nonCriticalExtension				UE-EUTRA-Capability-v1250-IEs			OPTIONAL
}

UE-EUTRA-Capability-v1250-IEs ::=	SEQUENCE {
	phyLayerParameters-v1250			PhyLayerParameters-v1250				OPTIONAL,
	rf-Parameters-v1250					RF-Parameters-v1250						OPTIONAL,
	rlc-Parameters-r12					RLC-Parameters-r12						OPTIONAL,
	ue-BasedNetwPerfMeasParameters-v1250	UE-BasedNetwPerfMeasParameters-v1250	OPTIONAL,
	ue-CategoryDL-r12					INTEGER (0..14)							OPTIONAL,
	ue-CategoryUL-r12					INTEGER (0..13)							OPTIONAL,
	wlan-IW-Parameters-r12				WLAN-IW-Parameters-r12					OPTIONAL,
	measParameters-v1250				MeasParameters-v1250					OPTIONAL,
	dc-Parameters-r12					DC-Parameters-r12						OPTIONAL,
	mbms-Parameters-v1250				MBMS-Parameters-v1250					OPTIONAL,
	mac-Parameters-r12					MAC-Parameters-r12						OPTIONAL,
	fdd-Add-UE-EUTRA-Capabilities-v1250	UE-EUTRA-CapabilityAddXDD-Mode-v1250	OPTIONAL,
	tdd-Add-UE-EUTRA-Capabilities-v1250	UE-EUTRA-CapabilityAddXDD-Mode-v1250	OPTIONAL,
	sl-Parameters-r12				SL-Parameters-r12					OPTIONAL,
	nonCriticalExtension				UE-EUTRA-Capability-v1260-IEs			OPTIONAL
}

UE-EUTRA-Capability-v1260-IEs ::=	SEQUENCE {
	ue-CategoryDL-v1260					INTEGER (15..16)						OPTIONAL,
	nonCriticalExtension				UE-EUTRA-Capability-v1270-IEs			OPTIONAL
}

UE-EUTRA-Capability-v1270-IEs ::= SEQUENCE {
	rf-Parameters-v1270					RF-Parameters-v1270						OPTIONAL,
	nonCriticalExtension				UE-EUTRA-Capability-v1280-IEs			OPTIONAL
}

UE-EUTRA-Capability-v1280-IEs ::= SEQUENCE {
	phyLayerParameters-v1280			PhyLayerParameters-v1280				OPTIONAL,
	nonCriticalExtension				UE-EUTRA-Capability-v13x0-IEs 			OPTIONAL
}

UE-EUTRA-Capability-v13x0-IEs ::= SEQUENCE {
	dc-Parameters-v13x0					DC-Parameters-v13x0						OPTIONAL,
	measParameters-v13xy				MeasParameters-v13xy					OPTIONAL,
	mac-Parameters-v13x0				MAC-Parameters-v13x0					OPTIONAL,
	pdcp-Parameters-v13x0			PDCP-Parameters-v13x0				OPTIONAL,
	phyLayerParameters-v13x0			PhyLayerParameters-v13x0				OPTIONAL,
	rf-Parameters-v13x0				RF-Parameters-v13x0					OPTIONAL,
	rlc-Parameters-v13x0				RLC-Parameters-v13x0					OPTIONAL,
	ue-CategoryDL-v13x0				INTEGER (17)							OPTIONAL,
	ue-CategoryUL-v13x0				INTEGER (14)							OPTIONAL,
	scptm-Parameters-v13x0				SCPTM-Parameters-v13x0					OPTIONAL,
	sl-Parameters-r13				SL-Parameters-r13					OPTIONAL,
	supportOfLAA-r13					ENUMERATED {supported}					OPTIONAL,
	nonCriticalExtension				SEQUENCE {}							OPTIONAL
}

UE-EUTRA-CapabilityAddXDD-Mode-r9 ::=	SEQUENCE {
	phyLayerParameters-r9				PhyLayerParameters					OPTIONAL,
	featureGroupIndicators-r9			BIT STRING (SIZE (32))				OPTIONAL,
	featureGroupIndRel9Add-r9			BIT STRING (SIZE (32))				OPTIONAL,
	interRAT-ParametersGERAN-r9			IRAT-ParametersGERAN				OPTIONAL,
	interRAT-ParametersUTRA-r9			IRAT-ParametersUTRA-v920			OPTIONAL,
	interRAT-ParametersCDMA2000-r9		IRAT-ParametersCDMA2000-1XRTT-v920	OPTIONAL,
	neighCellSI-AcquisitionParameters-r9	NeighCellSI-AcquisitionParameters-r9	OPTIONAL,
	...
}

UE-EUTRA-CapabilityAddXDD-Mode-v1060 ::=	SEQUENCE {
	phyLayerParameters-v1060			PhyLayerParameters-v1020			OPTIONAL,
	featureGroupIndRel10-v1060			BIT STRING (SIZE (32))				OPTIONAL,
	interRAT-ParametersCDMA2000-v1060	IRAT-ParametersCDMA2000-1XRTT-v1020	OPTIONAL,
	interRAT-ParametersUTRA-TDD-v1060	IRAT-ParametersUTRA-TDD-v1020		OPTIONAL,
	...,
	[[	otdoa-PositioningCapabilities-r10	OTDOA-PositioningCapabilities-r10	OPTIONAL
	]]
}

UE-EUTRA-CapabilityAddXDD-Mode-v1130 ::=	SEQUENCE {
	phyLayerParameters-v1130			PhyLayerParameters-v1130			OPTIONAL,
	measParameters-v1130				MeasParameters-v1130				OPTIONAL,
	otherParameters-r11					Other-Parameters-r11				OPTIONAL,
	...
}

UE-EUTRA-CapabilityAddXDD-Mode-v1180 ::=	SEQUENCE {
	mbms-Parameters-r11					MBMS-Parameters-r11
}

UE-EUTRA-CapabilityAddXDD-Mode-v1250 ::=	SEQUENCE {
	phyLayerParameters-v1250			PhyLayerParameters-v1250			OPTIONAL,
	measParameters-v1250				MeasParameters-v1250				OPTIONAL
}

AccessStratumRelease ::=			ENUMERATED {
										rel8, rel9, rel10, rel11, rel12, spare3,
										spare2, spare1, ...}

DC-Parameters-r12 ::=			SEQUENCE {
	drb-TypeSplit-r12						ENUMERATED {supported}			OPTIONAL,
	drb-TypeSCG-r12							ENUMERATED {supported}			OPTIONAL
}

DC-Parameters-v13x0 ::=			SEQUENCE {
	pdcp-TransferSplitUL-r13				ENUMERATED {supported}			OPTIONAL,
	ue-SSTD-Meas-r13						ENUMERATED {supported}			OPTIONAL
}

MAC-Parameters-r12 ::=				SEQUENCE {
	logicalChannelSR-ProhibitTimer-r12	ENUMERATED {supported}				OPTIONAL,
	longDRX-Command-r12				ENUMERATED {supported}					OPTIONAL
}

MAC-Parameters-v13x0 ::=				SEQUENCE {
	extendedMAC-LengthField-r13		ENUMERATED {supported}				OPTIONAL,
	extendedLongDRX-r13				ENUMERATED {supported}				OPTIONAL
}

RLC-Parameters-r12 ::=				SEQUENCE {
	extended-RLC-LI-Field-r12			ENUMERATED {supported}
}

RLC-Parameters-v13x0 ::=				SEQUENCE {
	extendedRLC-SN-SO-Field-r13				ENUMERATED {supported}
}

PDCP-Parameters ::=				SEQUENCE {
	supportedROHC-Profiles				SEQUENCE {
		profile0x0001						BOOLEAN,
		profile0x0002						BOOLEAN,
		profile0x0003						BOOLEAN,
		profile0x0004						BOOLEAN,
		profile0x0006						BOOLEAN,
		profile0x0101						BOOLEAN,
		profile0x0102						BOOLEAN,
		profile0x0103						BOOLEAN,
		profile0x0104						BOOLEAN
	},
	maxNumberROHC-ContextSessions		ENUMERATED {
											cs2, cs4, cs8, cs12, cs16, cs24, cs32,
											cs48, cs64, cs128, cs256, cs512, cs1024,
											cs16384, spare2, spare1}				DEFAULT cs16,
	...
}

PDCP-Parameters-v1130 ::=		SEQUENCE {
	pdcp-SN-Extension-r11					ENUMERATED {supported}			OPTIONAL,
	supportRohcContextContinue-r11			ENUMERATED {supported}			OPTIONAL
}

PDCP-Parameters-v13x0 ::=				SEQUENCE {
	pdcp-SN-Extension-18bits-r13			ENUMERATED {supported}
}

PhyLayerParameters ::=				SEQUENCE {
	ue-TxAntennaSelectionSupported		BOOLEAN,
	ue-SpecificRefSigsSupported		BOOLEAN
}

PhyLayerParameters-v920 ::=		SEQUENCE {
	enhancedDualLayerFDD-r9			ENUMERATED {supported}			OPTIONAL,
	enhancedDualLayerTDD-r9			ENUMERATED {supported}			OPTIONAL
}

PhyLayerParameters-v9d0 ::=			SEQUENCE {
	tm5-FDD-r9						ENUMERATED {supported}			OPTIONAL,
	tm5-TDD-r9						ENUMERATED {supported}			OPTIONAL
}

PhyLayerParameters-v1020 ::=			SEQUENCE {
	twoAntennaPortsForPUCCH-r10				ENUMERATED {supported}					OPTIONAL,
	tm9-With-8Tx-FDD-r10					ENUMERATED {supported}					OPTIONAL,
	pmi-Disabling-r10						ENUMERATED {supported}					OPTIONAL,
	crossCarrierScheduling-r10				ENUMERATED {supported}					OPTIONAL,
	simultaneousPUCCH-PUSCH-r10				ENUMERATED {supported}					OPTIONAL,
	multiClusterPUSCH-WithinCC-r10			ENUMERATED {supported}					OPTIONAL,
	nonContiguousUL-RA-WithinCC-List-r10	NonContiguousUL-RA-WithinCC-List-r10	OPTIONAL
}

PhyLayerParameters-v1130 ::=			SEQUENCE {
	crs-InterfHandl-r11						ENUMERATED {supported}					OPTIONAL,
	ePDCCH-r11								ENUMERATED {supported}					OPTIONAL,
	multiACK-CSI-Reporting-r11				ENUMERATED {supported}					OPTIONAL,
	ss-CCH-InterfHandl-r11					ENUMERATED {supported}					OPTIONAL,
	tdd-SpecialSubframe-r11					ENUMERATED {supported}					OPTIONAL,
	txDiv-PUCCH1b-ChSelect-r11				ENUMERATED {supported}					OPTIONAL,
	ul-CoMP-r11								ENUMERATED {supported}					OPTIONAL
}

PhyLayerParameters-v1170 ::=			SEQUENCE {
	interBandTDD-CA-WithDifferentConfig-r11	BIT STRING (SIZE (2))			OPTIONAL
}

PhyLayerParameters-v1250 ::=			SEQUENCE {
	e-HARQ-Pattern-FDD-r12					ENUMERATED {supported}			OPTIONAL,
	enhanced-4TxCodebook-r12				ENUMERATED {supported}			OPTIONAL,
	tdd-FDD-CA-PCellDuplex-r12				BIT STRING (SIZE (2))			OPTIONAL,
	phy-TDD-ReConfig-TDD-PCell-r12			ENUMERATED {supported}			OPTIONAL,
	phy-TDD-ReConfig-FDD-PCell-r12			ENUMERATED {supported}			OPTIONAL,
	pusch-FeedbackMode-r12					ENUMERATED {supported}			OPTIONAL,
	pusch-SRS-PowerControl-SubframeSet-r12	ENUMERATED {supported}			OPTIONAL,
	csi-SubframeSet-r12						ENUMERATED {supported}			OPTIONAL,
	noResourceRestrictionForTTIBundling-r12	ENUMERATED {supported}			OPTIONAL,
	discoverySignalsInDeactSCell-r12		ENUMERATED {supported}			OPTIONAL,
	naics-Capability-List-r12				NAICS-Capability-List-r12		OPTIONAL
}

PhyLayerParameters-v1280 ::=			SEQUENCE {
	alternativeTBS-Indices-r12				ENUMERATED {supported}			OPTIONAL
}
PhyLayerParameters-v13x0 ::=			SEQUENCE {
	codebook-HARQ-ACK-r13					BIT STRING (SIZE (2))			OPTIONAL,
	fdd-Harq-TimingTDD-r13					ENUMERATED {supported}			OPTIONAL,	maxNumberUpdatedCSI-Proc-r13				INTEGER(5..32)					OPTIONAL,
	supportedBlindDecoding-r13				INTEGER(1..32)					OPTIONAL,
	pucch-Format4-r13						ENUMERATED {supported}			OPTIONAL,
	pucch-Format5-r13						ENUMERATED {supported}			OPTIONAL,
	pucch-SCell-r13							ENUMERATED {supported}			OPTIONAL
}

NonContiguousUL-RA-WithinCC-List-r10 ::= SEQUENCE (SIZE (1..maxBands)) OF NonContiguousUL-RA-WithinCC-r10

NonContiguousUL-RA-WithinCC-r10 ::=		SEQUENCE {
	nonContiguousUL-RA-WithinCC-Info-r10	ENUMERATED {supported}					OPTIONAL
}

RF-Parameters ::=					SEQUENCE {
	supportedBandListEUTRA				SupportedBandListEUTRA
}

RF-Parameters-v9e0 ::=					SEQUENCE {
	supportedBandListEUTRA-v9e0				SupportedBandListEUTRA-v9e0				OPTIONAL
}

RF-Parameters-v1020 ::=				SEQUENCE {
	supportedBandCombination-r10			SupportedBandCombination-r10
}

RF-Parameters-v1060 ::=				SEQUENCE {
	supportedBandCombinationExt-r10			SupportedBandCombinationExt-r10
}

RF-Parameters-v1090 ::=					SEQUENCE {
	supportedBandCombination-v1090			SupportedBandCombination-v1090			OPTIONAL
}

RF-Parameters-v10f0 ::=					SEQUENCE {
	modifiedMPR-Behavior-r10					BIT STRING (SIZE (32))				OPTIONAL
}

RF-Parameters-v10i0 ::=					SEQUENCE {
	supportedBandCombination-v10i0			SupportedBandCombination-v10i0			OPTIONAL
}

RF-Parameters-v10j0 ::=					SEQUENCE {
	multiNS-Pmax-r10						ENUMERATED {supported}					OPTIONAL
}

RF-Parameters-v1130 ::=				SEQUENCE {
	supportedBandCombination-v1130			SupportedBandCombination-v1130			OPTIONAL
}

RF-Parameters-v1180 ::=				SEQUENCE {
	freqBandRetrieval-r11					ENUMERATED {supported}			OPTIONAL,
	requestedBands-r11						SEQUENCE (SIZE (1.. maxBands)) OF FreqBandIndicator-r11						OPTIONAL,
	supportedBandCombinationAdd-r11			SupportedBandCombinationAdd-r11		OPTIONAL
}

RF-Parameters-v11d0 ::=					SEQUENCE {
	supportedBandCombinationAdd-v11d0		SupportedBandCombinationAdd-v11d0		OPTIONAL
}

RF-Parameters-v1250 ::=				SEQUENCE {
	supportedBandListEUTRA-v1250				SupportedBandListEUTRA-v1250		OPTIONAL,
	supportedBandCombination-v1250			SupportedBandCombination-v1250			OPTIONAL,
	supportedBandCombinationAdd-v1250		SupportedBandCombinationAdd-v1250		OPTIONAL,
	freqBandPriorityAdjustment-r12			ENUMERATED {supported}					OPTIONAL
}

RF-Parameters-v1270 ::=				SEQUENCE {
	supportedBandCombination-v1270			SupportedBandCombination-v1270			OPTIONAL,
	supportedBandCombinationAdd-v1270		SupportedBandCombinationAdd-v1270		OPTIONAL
}

RF-Parameters-v13x0 ::=				SEQUENCE {
	requestedMaximumCCs-r13					ENUMERATED {supported, includedUL,
													includedDL, includedBoth}		OPTIONAL,
	skipFallbackCombinations-r13				ENUMERATED {supported, included}				OPTIONAL,
	supportedBandCombinations-r13		SupportedBandCombinations-r13				OPTIONAL, 
	supportedMIMO-CapabilityDL-r13		MIMO-CapabilityDL-r10						OPTIONAL
}
SupportedBandCombination-r10 ::= SEQUENCE (SIZE (1..maxBandComb-r10)) OF BandCombinationParameters-r10 

SupportedBandCombinationExt-r10 ::= SEQUENCE (SIZE (1..maxBandComb-r10)) OF BandCombinationParametersExt-r10

SupportedBandCombination-v1090 ::= SEQUENCE (SIZE (1..maxBandComb-r10)) OF BandCombinationParameters-v1090

SupportedBandCombination-v10i0 ::= SEQUENCE (SIZE (1..maxBandComb-r10)) OF BandCombinationParameters-v10i0

SupportedBandCombination-v1130 ::= SEQUENCE (SIZE (1..maxBandComb-r10)) OF BandCombinationParameters-v1130

SupportedBandCombination-v1250 ::= SEQUENCE (SIZE (1..maxBandComb-r10)) OF BandCombinationParameters-v1250

SupportedBandCombination-v1270 ::= SEQUENCE (SIZE (1..maxBandComb-r10)) OF BandCombinationParameters-v1270

SupportedBandCombinationAdd-r11 ::= SEQUENCE (SIZE (1..maxBandComb-r11)) OF BandCombinationParameters-r11

SupportedBandCombinationAdd-v11d0 ::= SEQUENCE (SIZE (1..maxBandComb-r11)) OF BandCombinationParameters-v10i0

SupportedBandCombinationAdd-v1250 ::= SEQUENCE (SIZE (1..maxBandComb-r11)) OF BandCombinationParameters-v1250

SupportedBandCombinationAdd-v1270 ::= SEQUENCE (SIZE (1..maxBandComb-r11)) OF BandCombinationParameters-v1270



SupportedBandCombinations-r13 ::=	SEQUENCE {
	bandCombinationList-r13						BandCombinationList-r13
}

BandCombinationList-r13 ::= SEQUENCE (SIZE (maxBandComb-r13)) OF BandCombination-r13

BandCombination-r13 ::=		SEQUENCE {
	additionalFallbackSupported-r13		ENUMERATED {true}				OPTIONAL,
	bandCombinationParameters-r13		BandCombinationParametersCommon-r13
}

BandCombinationParametersCommon-r13 ::= SEQUENCE {
	bandParameterList-r13			SEQUENCE (SIZE (1..maxSimultaneousBands-r10)) OF BandParameters-r13,
	supportedBandwidthCombinationSet-r13		SupportedBandwidthCombinationSet-r10		OPTIONAL,
	multipleTimingAdvance-r13		ENUMERATED {supported}					OPTIONAL,
	simultaneousRx-Tx-r13			ENUMERATED {supported}					OPTIONAL,
	bandInfoEUTRA-r13				BandInfoEUTRA,
	dc-Support-r13					SEQUENCE {
		asynchronous-r13			ENUMERATED {supported}			OPTIONAL,
		supportedCellGrouping-r13		CHOICE {
				threeEntries-r13				BIT STRING (SIZE(3)),
				fourEntries-r13					BIT STRING (SIZE(7)),
				fiveEntries-r13					BIT STRING (SIZE(15))
		}																OPTIONAL
	}																	OPTIONAL,
	supportedNAICS-2CRS-AP-r13		BIT STRING (SIZE (1..maxNAICS-Entries-r12))		OPTIONAL,
	commSupportedBandsPerBC-r13		BIT STRING (SIZE (1.. maxBands))		OPTIONAL
}


BandCombinationParameters-r10 ::= SEQUENCE (SIZE (1..maxSimultaneousBands-r10)) OF BandParameters-r10

BandCombinationParametersExt-r10 ::= SEQUENCE {
	supportedBandwidthCombinationSet-r10	SupportedBandwidthCombinationSet-r10	OPTIONAL
}

BandCombinationParameters-v1090 ::= SEQUENCE (SIZE (1..maxSimultaneousBands-r10)) OF BandParameters-v1090

BandCombinationParameters-v10i0::= SEQUENCE {
bandParameterList-v10i0			SEQUENCE (SIZE (1..maxSimultaneousBands-r10)) OF 
			BandParameters-v10i0	OPTIONAL
}

BandCombinationParameters-v1130 ::=	SEQUENCE {
	multipleTimingAdvance-r11		ENUMERATED {supported}					OPTIONAL,
	simultaneousRx-Tx-r11			ENUMERATED {supported}					OPTIONAL,
	bandParameterList-r11			SEQUENCE (SIZE (1..maxSimultaneousBands-r10)) OF BandParameters-v1130	OPTIONAL,
	...
}

BandCombinationParameters-r11 ::=	SEQUENCE {
	bandParameterList-r11			SEQUENCE (SIZE (1..maxSimultaneousBands-r10)) OF 
			BandParameters-r11,
	supportedBandwidthCombinationSet-r11	SupportedBandwidthCombinationSet-r10	OPTIONAL,
	multipleTimingAdvance-r11		ENUMERATED {supported}					OPTIONAL,
	simultaneousRx-Tx-r11			ENUMERATED {supported}					OPTIONAL,
	bandInfoEUTRA-r11				BandInfoEUTRA,
	...
}

BandCombinationParameters-v1250::= SEQUENCE {
	dc-Support-r12					SEQUENCE {
		asynchronous-r12				ENUMERATED {supported}			OPTIONAL,
		supportedCellGrouping-r12		CHOICE {
				threeEntries-r12				BIT STRING (SIZE(3)),
				fourEntries-r12					BIT STRING (SIZE(7)),
				fiveEntries-r12					BIT STRING (SIZE(15))
		}																OPTIONAL
	}																	OPTIONAL,
	supportedNAICS-2CRS-AP-r12		BIT STRING (SIZE (1..maxNAICS-Entries-r12))		OPTIONAL,
	commSupportedBandsPerBC-r12				BIT STRING (SIZE (1.. maxBands))		OPTIONAL,
	...
}

BandCombinationParameters-v1270 ::= SEQUENCE {
	bandParameterList-v1270			SEQUENCE (SIZE (1..maxSimultaneousBands-r10)) OF 
			BandParameters-v1270		OPTIONAL
}


SupportedBandwidthCombinationSet-r10 ::=	BIT STRING (SIZE (1..maxBandwidthCombSet-r10))

BandParameters-r10 ::= SEQUENCE {
	bandEUTRA-r10					FreqBandIndicator,
	bandParametersUL-r10			BandParametersUL-r10					OPTIONAL,
	bandParametersDL-r10			BandParametersDL-r10					OPTIONAL
}

BandParameters-v1090 ::= SEQUENCE {
	bandEUTRA-v1090					FreqBandIndicator-v9e0					OPTIONAL,
	...
}

BandParameters-v10i0::= SEQUENCE {
	bandParametersDL-v10i0		SEQUENCE (SIZE (1..maxBandwidthClass-r10)) OF CA-MIMO-ParametersDL-v10i0
}

BandParameters-v1130 ::= SEQUENCE {
	supportedCSI-Proc-r11			ENUMERATED {n1, n3, n4}
}

BandParameters-r11 ::= SEQUENCE {
	bandEUTRA-r11					FreqBandIndicator-r11,
	bandParametersUL-r11			BandParametersUL-r10					OPTIONAL,
	bandParametersDL-r11			BandParametersDL-r10					OPTIONAL,
	supportedCSI-Proc-r11			ENUMERATED {n1, n3, n4}					OPTIONAL
}

BandParameters-v1270 ::= SEQUENCE {
	bandParametersDL-v1270			SEQUENCE (SIZE (1..maxBandwidthClass-r10)) OF CA-MIMO-ParametersDL-v1270
}

BandParameters-r13 ::= SEQUENCE {
	bandEUTRA-r13					FreqBandIndicator-r11,
	bandParametersUL-r13				BandParametersUL-r13				OPTIONAL,
	bandParametersDL-r13				BandParametersDL-r13				OPTIONAL,
	supportedCSI-Proc-r13			ENUMERATED {n1, n3, n4}			OPTIONAL
}

BandParametersUL-r10 ::= SEQUENCE (SIZE (1..maxBandwidthClass-r10)) OF CA-MIMO-ParametersUL-r10

BandParametersUL-r13 ::= SEQUENCE OF CA-MIMO-ParametersUL-r10


CA-MIMO-ParametersUL-r10 ::= SEQUENCE {
	ca-BandwidthClassUL-r10				CA-BandwidthClass-r10,
	supportedMIMO-CapabilityUL-r10		MIMO-CapabilityUL-r10				OPTIONAL
}

BandParametersDL-r10 ::= SEQUENCE (SIZE (1..maxBandwidthClass-r10)) OF CA-MIMO-ParametersDL-r10

BandParametersDL-r13 ::= SEQUENCE OF CA-MIMO-ParametersDL-r13

CA-MIMO-ParametersDL-r10 ::= SEQUENCE {
	ca-BandwidthClassDL-r10				CA-BandwidthClass-r10,
	supportedMIMO-CapabilityDL-r10		MIMO-CapabilityDL-r10				OPTIONAL
}

CA-MIMO-ParametersDL-v10i0 ::= SEQUENCE {
	fourLayerTM3-TM4-r10				ENUMERATED {supported}				OPTIONAL
}

CA-MIMO-ParametersDL-v1270 ::= SEQUENCE {
	intraBandContiguousCC-InfoList-r12			SEQUENCE (SIZE (1..maxServCell-r10)) OF IntraBandContiguousCC-Info-r12
}

CA-MIMO-ParametersDL-r13 ::= SEQUENCE {
	ca-BandwidthClassDL-r13					CA-BandwidthClass-r10,
	supportedMIMO-CapabilityDL-r13			MIMO-CapabilityDL-r10				OPTIONAL,
	fourLayerTM3-TM4-r13						ENUMERATED {supported}				OPTIONAL,
	intraBandContiguousCC-InfoList-r13		SEQUENCE (SIZE (1..maxServCell-r13)) OF IntraBandContiguousCC-Info-r12
}

IntraBandContiguousCC-Info-r12 ::= SEQUENCE {
	fourLayerTM3-TM4-perCC-r12			ENUMERATED {supported}				OPTIONAL,
	supportedMIMO-CapabilityDL-r12		MIMO-CapabilityDL-r10				OPTIONAL,
	supportedCSI-Proc-r12				ENUMERATED {n1, n3, n4}				OPTIONAL
}

CA-BandwidthClass-r10 ::= ENUMERATED {a, b, c, d, e, f, ...}

MIMO-CapabilityUL-r10 ::= ENUMERATED {twoLayers, fourLayers}

MIMO-CapabilityDL-r10 ::= ENUMERATED {twoLayers, fourLayers, eightLayers}

SupportedBandListEUTRA ::=			SEQUENCE (SIZE (1..maxBands)) OF SupportedBandEUTRA 

SupportedBandListEUTRA-v9e0::=			SEQUENCE (SIZE (1..maxBands)) OF SupportedBandEUTRA-v9e0

SupportedBandListEUTRA-v1250 ::=		SEQUENCE (SIZE (1..maxBands)) OF SupportedBandEUTRA-v1250

SupportedBandEUTRA ::=				SEQUENCE {
	bandEUTRA							FreqBandIndicator,
	halfDuplex							BOOLEAN
}

SupportedBandEUTRA-v9e0 ::=		SEQUENCE {
	bandEUTRA-v9e0						FreqBandIndicator-v9e0		OPTIONAL
}

SupportedBandEUTRA-v1250 ::=		SEQUENCE {
	dl-256QAM-r12						ENUMERATED {supported}		OPTIONAL,
	ul-64QAM-r12						ENUMERATED {supported}		OPTIONAL
}

MeasParameters ::=					SEQUENCE {
	bandListEUTRA						BandListEUTRA
}

MeasParameters-v1020 ::=			SEQUENCE {
	bandCombinationListEUTRA-r10			BandCombinationListEUTRA-r10
}

MeasParameters-v1130 ::=			SEQUENCE {
	rsrqMeasWideband-r11			ENUMERATED {supported}					OPTIONAL
}

MeasParameters-v11a0 ::=			SEQUENCE {
	benefitsFromInterruption-r11			ENUMERATED {true}				OPTIONAL
}

MeasParameters-v1250 ::=			SEQUENCE {	
	timerT312-r12						ENUMERATED {supported}		OPTIONAL,
	alternativeTimeToTrigger-r12		ENUMERATED {supported}		OPTIONAL,
	incMonEUTRA-r12						ENUMERATED {supported}		OPTIONAL,
	incMonUTRA-r12						ENUMERATED {supported}		OPTIONAL,
	extendedMaxMeasId-r12				ENUMERATED {supported}		OPTIONAL,
	extendedRSRQ-LowerRange-r12			ENUMERATED {supported}		OPTIONAL,
	rsrq-OnAllSymbols-r12				ENUMERATED {supported}		OPTIONAL,
	crs-DiscoverySignalsMeas-r12		ENUMERATED {supported}		OPTIONAL,
	csi-RS-DiscoverySignalsMeas-r12		ENUMERATED {supported}		OPTIONAL
}

MeasParameters-v13xy ::=			SEQUENCE {
	rs-SINR-Meas-r13					ENUMERATED {supported}		OPTIONAL,
	whiteCellList-r13		ENUMERATED {supported}		OPTIONAL
}

BandListEUTRA ::=					SEQUENCE (SIZE (1..maxBands)) OF BandInfoEUTRA 

BandCombinationListEUTRA-r10 ::=	SEQUENCE (SIZE (1..maxBandComb-r10)) OF BandInfoEUTRA

BandInfoEUTRA ::=					SEQUENCE {
	interFreqBandList					InterFreqBandList,
	interRAT-BandList					InterRAT-BandList		OPTIONAL
}

InterFreqBandList ::=				SEQUENCE (SIZE (1..maxBands)) OF InterFreqBandInfo

InterFreqBandInfo ::=				SEQUENCE {
	interFreqNeedForGaps				BOOLEAN
}

InterRAT-BandList ::=				SEQUENCE (SIZE (1..maxBands)) OF InterRAT-BandInfo

InterRAT-BandInfo ::=				SEQUENCE {
	interRAT-NeedForGaps				BOOLEAN
}

IRAT-ParametersUTRA-FDD ::=		SEQUENCE {
	supportedBandListUTRA-FDD			SupportedBandListUTRA-FDD
}

IRAT-ParametersUTRA-v920 ::=		SEQUENCE {
	e-RedirectionUTRA-r9				ENUMERATED {supported}
}

IRAT-ParametersUTRA-v9c0 ::=		SEQUENCE {
	voiceOverPS-HS-UTRA-FDD-r9						ENUMERATED {supported}		OPTIONAL,
	voiceOverPS-HS-UTRA-TDD128-r9					ENUMERATED {supported}		OPTIONAL,
	srvcc-FromUTRA-FDD-ToUTRA-FDD-r9				ENUMERATED {supported}		OPTIONAL,
	srvcc-FromUTRA-FDD-ToGERAN-r9					ENUMERATED {supported}		OPTIONAL,
	srvcc-FromUTRA-TDD128-ToUTRA-TDD128-r9			ENUMERATED {supported}		OPTIONAL,
	srvcc-FromUTRA-TDD128-ToGERAN-r9				ENUMERATED {supported}		OPTIONAL
}

IRAT-ParametersUTRA-v9h0 ::=		SEQUENCE {
	mfbi-UTRA-r9						ENUMERATED {supported}
}

SupportedBandListUTRA-FDD ::=		SEQUENCE (SIZE (1..maxBands)) OF SupportedBandUTRA-FDD 

SupportedBandUTRA-FDD ::=			ENUMERATED {
										bandI, bandII, bandIII, bandIV, bandV, bandVI,
										bandVII, bandVIII, bandIX, bandX, bandXI,
										bandXII, bandXIII, bandXIV, bandXV, bandXVI, ...,
										bandXVII-8a0, bandXVIII-8a0, bandXIX-8a0, bandXX-8a0,
										bandXXI-8a0, bandXXII-8a0, bandXXIII-8a0, bandXXIV-8a0,
										bandXXV-8a0, bandXXVI-8a0, bandXXVII-8a0, bandXXVIII-8a0,
										bandXXIX-8a0, bandXXX-8a0, bandXXXI-8a0, bandXXXII-8a0}

IRAT-ParametersUTRA-TDD128 ::=		SEQUENCE {
	supportedBandListUTRA-TDD128		SupportedBandListUTRA-TDD128
}

SupportedBandListUTRA-TDD128 ::=	SEQUENCE (SIZE (1..maxBands)) OF SupportedBandUTRA-TDD128 

SupportedBandUTRA-TDD128 ::=		ENUMERATED {
										a, b, c, d, e, f, g, h, i, j, k, l, m, n,
										o, p, ...}

IRAT-ParametersUTRA-TDD384 ::=		SEQUENCE {
	supportedBandListUTRA-TDD384		SupportedBandListUTRA-TDD384
}

SupportedBandListUTRA-TDD384 ::=	SEQUENCE (SIZE (1..maxBands)) OF SupportedBandUTRA-TDD384 

SupportedBandUTRA-TDD384 ::=		ENUMERATED {
											a, b, c, d, e, f, g, h, i, j, k, l, m, n,
											o, p, ...}

IRAT-ParametersUTRA-TDD768 ::=		SEQUENCE {
	supportedBandListUTRA-TDD768		SupportedBandListUTRA-TDD768
}

SupportedBandListUTRA-TDD768 ::=	SEQUENCE (SIZE (1..maxBands)) OF SupportedBandUTRA-TDD768 

SupportedBandUTRA-TDD768 ::=		ENUMERATED {
										a, b, c, d, e, f, g, h, i, j, k, l, m, n,
										o, p, ...}

IRAT-ParametersUTRA-TDD-v1020 ::=		SEQUENCE {
	e-RedirectionUTRA-TDD-r10				ENUMERATED {supported}
}

IRAT-ParametersGERAN ::=			SEQUENCE {
	supportedBandListGERAN				SupportedBandListGERAN,
	interRAT-PS-HO-ToGERAN				BOOLEAN
}

IRAT-ParametersGERAN-v920 ::=		SEQUENCE {
	dtm-r9								ENUMERATED {supported}			OPTIONAL,
	e-RedirectionGERAN-r9				ENUMERATED {supported}			OPTIONAL
}

SupportedBandListGERAN ::=			SEQUENCE (SIZE (1..maxBands)) OF SupportedBandGERAN 

SupportedBandGERAN ::=				ENUMERATED {
										gsm450, gsm480, gsm710, gsm750, gsm810, gsm850,
										gsm900P, gsm900E, gsm900R, gsm1800, gsm1900,
										spare5, spare4, spare3, spare2, spare1, ...}

IRAT-ParametersCDMA2000-HRPD ::=	SEQUENCE {
	supportedBandListHRPD				SupportedBandListHRPD,
	tx-ConfigHRPD						ENUMERATED {single, dual},
	rx-ConfigHRPD						ENUMERATED {single, dual}
}

SupportedBandListHRPD ::=			SEQUENCE (SIZE (1..maxCDMA-BandClass)) OF BandclassCDMA2000

IRAT-ParametersCDMA2000-1XRTT ::=	SEQUENCE {
	supportedBandList1XRTT				SupportedBandList1XRTT,
	tx-Config1XRTT						ENUMERATED {single, dual},
	rx-Config1XRTT						ENUMERATED {single, dual}
}

IRAT-ParametersCDMA2000-1XRTT-v920 ::=	SEQUENCE {
	e-CSFB-1XRTT-r9						ENUMERATED {supported},
	e-CSFB-ConcPS-Mob1XRTT-r9			ENUMERATED {supported}			OPTIONAL
}

IRAT-ParametersCDMA2000-1XRTT-v1020 ::=	SEQUENCE {
	e-CSFB-dual-1XRTT-r10				ENUMERATED {supported}
}

IRAT-ParametersCDMA2000-v1130 ::=		SEQUENCE {
	cdma2000-NW-Sharing-r11					ENUMERATED {supported}		OPTIONAL
}

SupportedBandList1XRTT ::=			SEQUENCE (SIZE (1..maxCDMA-BandClass)) OF BandclassCDMA2000

CSG-ProximityIndicationParameters-r9 ::=	SEQUENCE {
	intraFreqProximityIndication-r9	ENUMERATED {supported}			OPTIONAL,
	interFreqProximityIndication-r9	ENUMERATED {supported}			OPTIONAL,
	utran-ProximityIndication-r9		ENUMERATED {supported}			OPTIONAL
}

NeighCellSI-AcquisitionParameters-r9 ::=	SEQUENCE {
	intraFreqSI-AcquisitionForHO-r9	ENUMERATED {supported}			OPTIONAL,
	interFreqSI-AcquisitionForHO-r9	ENUMERATED {supported}			OPTIONAL,
	utran-SI-AcquisitionForHO-r9		ENUMERATED {supported}			OPTIONAL
}

SON-Parameters-r9 ::=				SEQUENCE {
	rach-Report-r9						ENUMERATED {supported}			OPTIONAL
}

UE-BasedNetwPerfMeasParameters-r10 ::=	SEQUENCE {
	loggedMeasurementsIdle-r10				ENUMERATED {supported}		OPTIONAL,
	standaloneGNSS-Location-r10				ENUMERATED {supported}		OPTIONAL
}

UE-BasedNetwPerfMeasParameters-v1250 ::= 	SEQUENCE {
	loggedMBSFNMeasurements-r12				ENUMERATED {supported}
}

OTDOA-PositioningCapabilities-r10 ::=	SEQUENCE {
	otdoa-UE-Assisted-r10					ENUMERATED {supported},
	interFreqRSTD-Measurement-r10			ENUMERATED {supported}		OPTIONAL
}

Other-Parameters-r11 ::=				SEQUENCE {
	inDeviceCoexInd-r11						ENUMERATED {supported}		OPTIONAL,
	powerPrefInd-r11						ENUMERATED {supported}		OPTIONAL,
	ue-Rx-TxTimeDiffMeasurements-r11		ENUMERATED {supported}		OPTIONAL
}

Other-Parameters-v11d0 ::=				SEQUENCE {
	inDeviceCoexInd-UL-CA-r11				ENUMERATED {supported}		OPTIONAL
}

MBMS-Parameters-r11 ::=				SEQUENCE {
	mbms-SCell-r11							ENUMERATED {supported}		OPTIONAL,
	mbms-NonServingCell-r11					ENUMERATED {supported}		OPTIONAL
}

MBMS-Parameters-v1250 ::=				SEQUENCE {
	mbms-AsyncDC-r12						ENUMERATED {supported}		OPTIONAL
}

SCPTM-Parameters-v13x0 ::=				SEQUENCE {
	scptm-ParallelReception-r13					ENUMERATED {supported}		OPTIONAL
}

WLAN-IW-Parameters-r12 ::=	SEQUENCE {
	wlan-IW-RAN-Rules-r12					ENUMERATED {supported}		OPTIONAL,
	wlan-IW-ANDSF-Policies-r12						ENUMERATED {supported}		OPTIONAL
}

NAICS-Capability-List-r12 ::= SEQUENCE (SIZE (1..maxNAICS-Entries-r12)) OF NAICS-Capability-Entry-r12


NAICS-Capability-Entry-r12	::=	SEQUENCE {
	numberOfNAICS-CapableCC-r12				INTEGER(1..5),
	numberOfAggregatedPRB-r12				ENUMERATED {
												n50, n75, n100, n125, n150, n175, 
												n200, n225, n250, n275, n300, n350,
												n400, n450, n500, spare},
	...
}

SL-Parameters-r12 ::=				SEQUENCE {
	commSimultaneousTx-r12					ENUMERATED {supported}		OPTIONAL,
	commSupportedBands-r12					FreqBandIndicatorListEUTRA-r12 	OPTIONAL,
	discSupportedBands-r12					SupportedBandInfoList-r12 	OPTIONAL,
	discScheduledResourceAlloc-r12			ENUMERATED {supported}		OPTIONAL,
	disc-UE-SelectedResourceAlloc-r12		ENUMERATED {supported}		OPTIONAL,
	disc-SLSS-r12							ENUMERATED {supported}		OPTIONAL,
	discSupportedProc-r12					ENUMERATED {n50, n400}		OPTIONAL
}

SL-Parameters-r13 ::=				SEQUENCE {
	discSysInfoReporting-r13					ENUMERATED {supported}		OPTIONAL
}

SupportedBandInfoList-r12 ::=		SEQUENCE (SIZE (1..maxBands)) OF SupportedBandInfo-r12 

SupportedBandInfo-r12 ::=			SEQUENCE {
	support-r12								ENUMERATED {supported}	OPTIONAL
}

FreqBandIndicatorListEUTRA-r12 ::=		SEQUENCE (SIZE (1..maxBands)) OF FreqBandIndicator-r11

-- ASN1STOP


UE-EUTRA-Capability field descriptions
FDD/ TDD diff
accessStratumRelease
Set to rel12 in this version of the specification.
-
additionalFallbackSupported
Indicates that the UE supports different capabilities for at least one fallback case of this band combination.
-
alternativeTBS-Indices
Indicates whether the UE supports alternative TBS indices for ITBS 26 and 33 as specified in TS 36.213 [23].
-
alternativeTimeToTrigger
Indicates whether the UE supports alternativeTimeToTrigger.
No
bandCombinationListEUTRA
One entry corresponding to each supported band combination listed in the same order as in supportedBandCombination. 
-
BandCombinationParameters-v1090
If included, the UE shall include the same number of entries, and listed in the same order, as in BandCombinationParameters-r10.
-
BandCombinationParameters-v1130
The field is applicable to each supported CA bandwidth class combination (i.e. CA configuration in TS 36.101 [42, Section 5.6A.1]) indicated in the corresponding band combination. If included, the UE shall include the same number of entries, and listed in the same order, as in BandCombinationParameters-r10.
-
bandEUTRA
E-UTRA band as defined in TS 36.101 [42]. In case the UE includes bandEUTRA-v9e0 or bandEUTRA-v1090, the UE shall set the corresponding entry of bandEUTRA (i.e. without suffix) or bandEUTRA-r10 respectively to maxFBI.
-
bandListEUTRA
One entry corresponding to each supported E-UTRA band listed in the same order as in supportedBandListEUTRA.
-
bandParametersUL, bandParametersDL
Indicates the supported parameters for the band. UE shall indicate parameters for only one CA uplink or downlink bandwidth class in a single band entry for one band combination entry.
-
benefitsFromInterruption
Indicates whether the UE power consumption would benefit from being allowed to cause interruptions to serving cells when performing measurements of deactivated SCell carriers for measCycleSCell of less than 640ms, as specified in TS 36.133 [16].
No
CA-BandwidthClass
The CA bandwidth class supported by the UE as defined in TS 36.101 [42, Table 5.6A-1]. 
The UE explicitly includes all the supported CA bandwidth class combinations in the band combination signalling. Support for one CA bandwidth class does not implicitly indicate support for another CA bandwidth class.
-
cdma2000-NW-Sharing
Indicates whether the UE supports network sharing for CDMA2000.
-
codebook-HARQ-ACK
Indicates whether the UE supports determining HARQ ACK codebook size based on the DAI-ased solution and/or the number of configured CCs. The first bit is set to "1" if the UE supports the DAI-based codebook size determination. The second bit is set to "1" if the UE supports the codebook determination based on the number of configured CCs.
-
commSimultaneousTx
Indicates whether the UE supports simultaneous transmission of EUTRA and sidelink communication (on different carriers) in all bands for which the UE indicated sidelink support in a band combination (using commSupportedBandsPerBC).
-
commSupportedBands
Indicates the bands on which the UE supports sidelink communication, by an independent list of bands i.e. separate from the list of supported E UTRA band, as indicated in supportedBandListEUTRA.
-
commSupportedBandsPerBC
Indicates, for a particular band combination, the bands on which the UE supports simultaneous reception of EUTRA and sidelink communication. If the UE indicates support simultaneous transmission (using commSimultaneousTx), it also indicates, for a particular band combination, the bands on which the UE supports simultaneous transmission of EUTRA and sidelink communication. The first bit refers to the first band included in commSupportedBands, with value 1 indicating sidelink is supported.
-
crossCarrierScheduling
Yes
crs-DiscoverySignalsMeas
Indicates whether the UE supports CRS based discovery signals measurement, and PDSCH/EPDCCH RE mapping with zero power CSI-RS configured for discovery signals.
FFS
crs-InterfHandl
Indicates whether the UE supports CRS interference handling.
No
csi-RS-DiscoverySignalsMeas
Indicates whether the UE supports CSI-RS based discovery signals measurement. If this field is included, the UE shall also include crs-DiscoverySignalsMeas.
FFS
csi-SubframeSet
Indicates whether the UE supports REL-12 DL CSI subframe set configuration, REL-12 DL CSI subframe set dependent CSI measurement/feedback, configuration of up to 2 CSI-IM resources for a CSI process with no more than 4 CSI-IM resources for all CSI processes of one frequency if the UE supports tm10, configuration of two ZP-CSI-RS for tm1 to tm9, PDSCH RE mapping with two ZP-CSI-RS configurations, and EPDCCH RE mapping with two ZP-CSI-RS configurations if the UE supports EPDCCH. This field is only applicable for UEs supporting TDD. 
-
dc-Support
Including this field indicates that the UE supports synchronous DC and power control mode 1. Including this field for a band combination entry comprising of single band entry indicates that the UE supports intra-band contiguous DC. Including this field for a band combination entry comprising of two or more band entries, indicates that the UE supports DC for these bands and that the serving cells corresponding to a band entry shall belong to one cell group (i.e. MCG or SCG). Including field asynchronous indicates that the UE supports asynchronous DC and power control mode 2. Including this field for a TDD/FDD band combination indicates that the UE supports TDD/FDD DC for this band combination.
-
deviceType
UE may set the value to "noBenFromBatConsumpOpt" when it does not foresee to particularly benefit from NW-based battery consumption optimisation. Absence of this value means that the device does benefit from NW-based battery consumption optimisation.
-
discoverySignalsInDeactSCell
Indicates whether the UE supports the behaviour on DL signals and physical channels when SCell is deactivated and discovery signals measurement is configured as specified in TS 36.211 [17, 6.11A]. This field is included only if UE supports carrier aggregation and includes crs-DiscoverySignalsMeas.
FFS
discScheduledResourceAlloc
Indicates whether the UE supports transmission of discovery announcements based on network scheduled resource allocation.
-
disc-UE-SelectedResourceAlloc
Indicates whether the UE supports transmission of discovery announcements based on UE autonomous resource selection.
-
disc-SLSS
Indicates whether the UE supports Sidelink Synchronization Signal (SLSS) transmission and reception for sidelink discovery.
-
discSupportedBands
Indicates the bands on which the UE supports sidelink discovery. One entry corresponding to each supported E UTRA band, listed in the same order as in supportedBandListEUTRA.
-
discSupportedProc
Indicates the number of processes supported by the UE for sidelink discovery.
-
discSysInfoReporting
Indicates whether the UE supports reporting of System Information for inter-frequency/PLMN discovery	-
-
dl-256QAM
Indicates whether the UE supports 256QAM in DL on the band.
-
drb-TypeSCG, drb-TypeSplit
The drb-TypeSplit indicates whether the UE supports split bearer except for PDCP data transfer in UL. The drb-TypeSCG indicates whether the UE supports SCG bearer.
-
dtm
Indicates whether the UE supports DTM in GERAN.
-
e-CSFB-1XRTT
Indicates whether the UE supports enhanced CS fallback to CDMA2000 1xRTT or not.
Yes
e-CSFB-ConcPS-Mob1XRTT
Indicates whether the UE supports concurrent enhanced CS fallback to CDMA2000 1xRTT and PS handover/ redirection to CDMA2000 HRPD.
Yes
e-CSFB-dual-1XRTT
Indicates whether the UE supports enhanced CS fallback to CDMA2000 1xRTT for dual Rx/Tx configuration. This bit can only be set to supported if tx-Config1XRTT and rx-Config1XRTT are both set to dual.
Yes
e-HARQ-Pattern-FDD
Indicates whether the UE supports enhanced HARQ pattern for TTI bundling operation for FDD.
-
Enhanced-4TxCodebook
Indicates whether the UE supports enhanced 4Tx codebook.
No
enhancedDualLayerTDD
Indicates whether the UE supports enhanced dual layer (PDSCH transmission mode 8) for TDD or not.
-
ePDCCH
Indicates whether the UE can receive DCI on UE specific search space on Enhanced PDCCH.
Yes
e-RedirectionUTRA
Yes
e-RedirectionUTRA-TDD
Indicates whether the UE supports enhanced redirection to UTRA TDD to multiple carrier frequencies both with and without using related SIB provided by RRCConnectionRelease or not.
Yes
extendedLongDRX
Indicates whether the UE supporst extended long DRX cycles of 5.12s and 10.24s in connected mode
-
extendedMaxMeasId
Indicates whether the UE supports extended number of measurement identies as defined by maxMeasId-r12.
No
extended-RLC-LI-Field
Indicates whether the UE supports 15 bit RLC length indicator.
-
extended-RLC-SN-SO-Field
Indicates whether the UE supports 16 bits of RLC sequence number and segmentation offset.
-
extendedRSRQ-LowerRange
Indicates whether the UE supports the extended RSRQ lower value range from -34dB to -19.5dB in measurement configuration and reporting as specified in TS 36.133 [16].
No
fdd-Harq-TimingTDD
Indicates whether UE supports FDD HARQ timing for TDD SCell when configured with TDD PCell.
-
featureGroupIndicators, featureGroupIndRel9Add, featureGroupIndRel10
The definitions of the bits in the bit string are described in Annex B.1 (for featureGroupIndicators and featureGroupIndRel9Add) and in Annex C.1.(for featureGroupIndRel10)
Yes
fourLayerTM3-TM4
Indicates whether the UE supports 4-layer spatial multiplexing for TM3 and TM4.
-
fourLayerTM3-TM4-perCC
Indicates whether the UE supports 4-layer spatial multiplexing for TM3 and TM4 for the component carrier.
-
freqBandPriorityAdjustment
Indicates whether the UE supports the prioritization of frequency bands in multiBandInfoList over the band in freqBandIndicator as defined by freqBandIndicatorPriority-r12.
-
freqBandRetrieval
Indicates whether the UE supports reception of requestedFrequencyBands.
-
halfDuplex
If halfDuplex is set to true, only half duplex operation is supported for the band, otherwise full duplex operation is supported.
-
incMonEUTRA
Indicates whether the UE supports increased number of E-UTRA carrier monitoring in RRC_IDLE and RRC_CONNECTED, as specified in TS 36.133 [16].
No
incMonUTRA
Indicates whether the UE supports increased number of UTRA carrier monitoring in RRC_IDLE and RRC_CONNECTED, as specified in TS 36.133 [16].
No
inDeviceCoexInd
Indicates whether the UE supports in-device coexistence indication as well as autonomous denial functionality.
Yes
inDeviceCoexInd-UL-CA
Indicates whether the UE supports UL CA related in-device coexistence indication. This field can be included only if inDeviceCoexInd is included. The UE supports inDeviceCoexInd-UL-CA in the same duplexing modes as it supports inDeviceCoexInd.
-
interBandTDD-CA-WithDifferentConfig
Indicates whether the UE supports inter-band TDD carrier aggregation with different UL/DL configuration combinations. The first bit indicates UE supports the configuration combination of SCell DL subframes are a subset of PCell and PSCell by SIB1 configuration and the configuration combination of SCell DL subframes are a superset of PCell and PSCell by SIB1 configuration; the second bit indicates UE supports the configuration combination of SCell DL subframes are neither superset nor subset of PCell and PSCell by SIB1 configuration. This field is included only if UE supports inter-band TDD carrier aggregation.
-
interFreqBandList
One entry corresponding to each supported E-UTRA band listed in the same order as in supportedBandListEUTRA.
-
interFreqNeedForGaps
Indicates need for measurement gaps when operating on the E-UTRA band given by the entry in bandListEUTRA or on the E-UTRA band combination given by the entry in bandCombinationListEUTRA and measuring on the E-UTRA band given by the entry in interFreqBandList.
-
interFreqProximityIndication
Indicates whether the UE supports proximity indication for inter-frequency E-UTRAN CSG member cells.
-
interFreqRSTD-Measurement
Indicates whether the UE supports inter-frequency RSTD measurements for OTDOA positioning [54].
Yes
interFreqSI-AcquisitionForHO
Indicates whether the UE supports, upon configuration of si-RequestForHO by the network, acquisition and reporting of relevant information using autonomous gaps by reading the SI from a neighbouring inter-frequency cell.
Yes
interRAT-BandList
One entry corresponding to each supported band of another RAT listed in the same order as in the interRAT-Parameters.
-
interRAT-NeedForGaps
Indicates need for DL measurement gaps when operating on the E-UTRA band given by the entry in bandListEUTRA or on the E-UTRA band combination given by the entry in bandCombinationListEUTRA and measuring on the inter-RAT band given by the entry in the interRAT-BandList.
-
interRAT-PS-HO-ToGERAN
Indicates whether the UE supports inter-RAT PS handover to GERAN or not.
Yes
intraBandContiguousCC-InfoList
Indicates, per serving carrier of which the corresponding bandwidth class includes multiple serving carriers (i.e. bandwidth class B, C, D and so on), the maximum number of supported layers for spatial multiplexing in DL and the maximum number of CSI processes supported. The number of entries is equal to the number of component carriers in the corresponding bandwidth class. The UE shall support the setting indicated in each entry of the list regardless of the order of entries in the list.The UE shall include the field only if it supports 4-layer spatial multiplexing in transmission mode3/4 for a subset of component carriers in the corresponding bandwidth class, or if the maximum number of supported layers for at least one component carrier is higher than supportedMIMO-CapabilityDL-r10 in the corresponding bandwidth class, or if the number of CSI processes for at least one component carrier is higher than supportedCSI-Proc-r11 in the corresponding band.
-
intraFreqProximityIndication
Indicates whether the UE supports proximity indication for intra-frequency E-UTRAN CSG member cells.
-
intraFreqSI-AcquisitionForHO
Indicates whether the UE supports, upon configuration of si-RequestForHO by the network, acquisition and reporting of relevant information using autonomous gaps by reading the SI from a neighbouring intra-frequency cell.
Yes
loggedMBSFNMeasurements
Indicates whether the UE supports logged measurements for MBSFN. A UE indicating support for logged measurements for MBSFN shall also indicate support for logged measurements in Idle mode.
-
loggedMeasurementsIdle
Indicates whether the UE supports logged measurements in Idle mode.
-
logicalChannelSR-ProhibitTimer
Indicates whether the UE supports the logicalChannelSR-ProhibitTimer as defined in TS 36.321 [6].
-
longDRX-Command
Indicates whether the UE supports Long DRX Command MAC Control Element.
-
maxNumberROHC-ContextSessions
Set to the maximum number of concurrently active ROHC contexts supported by the UE, excluding context sessions that leave all headers uncompressed. cs2 corresponds with 2 (context sessions), cs4 corresponds with 4 and so on. The network ignores this field if the UE supports none of the ROHC profiles in supportedROHC-Profiles.
-
maxNumberUpdatedCSI
Indicates the maximum number of CSI processes to be updated across CCs.
-
mbms-AsyncDC
Indicates whether the UE in RRC_CONNECTED supports MBMS reception via MRB on a frequency indicated in an MBMSInterestIndication message, where (according to supportedBandCombination) the carriers that are or can be configured as serving cells in the MCG and the SCG are not synchronized. If this field is included, the UE shall also include mbms-SCell and mbms-NonServingCell.
TBD
mbms-SCell
Indicates whether the UE in RRC_CONNECTED supports MBMS reception via MRB on a frequency indicated in an MBMSInterestIndication message, when an SCell is configured on that frequency (regardless of whether the SCell is activated or deactivated).
Yes
mbms-NonServingCell
Indicates whether the UE in RRC_CONNECTED supports MBMS reception via MRB on a frequency indicated in an MBMSInterestIndication message, where (according to supportedBandCombination and to network synchronization properties) a serving cell may be additionally configured. If this field is included, the UE shall also include the mbms-SCell field.
Yes
mfbi-UTRA
It indicates if the UE supports the signalling requirements of multiple radio frequency bands in a UTRA FDD cell, as defined in TS 25.307 [65].
-
MIMO-CapabilityDL
The number of supported layers for spatial multiplexing in DL. The field may be absent for category 0 and category 1 UE in which case the number of supported layers is 1.
-
MIMO-CapabilityUL
The number of supported layers for spatial multiplexing in UL. Absence of the field means that the number of supported layers is 1.
-
modifiedMPR-Behavior
Field encoded as a bit map, where at least one bit N is set to "1" if UE supports modified MPR/A-MPR behaviour N, see TS 36.101 [42]. All remaining bits of the field are set to "0". The leading / leftmost bit (bit 0) corresponds to modified MPR/A-MPR behaviour 0, the next bit corresponds to modified MPR/A-MPR behaviour 1 and so on. 
Absence of this field means that UE does not support any modified MPR/A-MPR behaviour.
-
multiACK-CSIreporting
Indicates whether the UE supports multi-cell HARQ ACK and periodic CSI reporting and SR on PUCCH format 3.
Yes
multiClusterPUSCH-WithinCC
Yes
multiNS-Pmax
Indicates whether the UE supports the mechanisms defined for cells broadcasting NS-PmaxList.
-
multipleTimingAdvance
Indicates whether the UE supports multiple timing advances for each band combination listed in supportedBandCombination. If the band combination comprised of more than one band entry (i.e., inter-band or intra-band non-contiguous band combination), the field indicates that the same or different timing advances on different band entries are supported. If the band combination comprised of one band entry (i.e., intra-band contiguous band combination), the field indicates that the same or different timing advances across component carriers of the band entry are supported.
-
naics-Capability-List
Indicates that UE supports NAICS, i.e. receiving assistance information from serving cell and using it to cancel or suppress interference of neighbouring cell(s) for at least one band combination. If not present, UE does not support NAICS for any band combination. The field numberOfNAICS-CapableCC indicates the maximum number of component carriers where the NAICS processing is supported and the field numberOfAggregatedPRB indicates the maximum aggregated bandwidth across these of component carriers (expressed as a number of PRBs) with the restriction that NAICS is only supported over the full carrier bandwidth.
For numberOfNAICS-CapableCC = 1, UE signals one value for numberOfAggregatedPRB from the range {50, 75, 100};
For numberOfNAICS-CapableCC = 2, UE signals one value for numberOfAggregatedPRB from the range {50, 75, 100, 125, 150, 175, 200}; 
For numberOfNAICS-CapableCC = 3, UE signals one value for numberOfAggregatedPRB from the range {50, 75, 100, 125, 150, 175, 200, 225, 250, 275, 300}; 
For numberOfNAICS-CapableCC = 4, UE signals one value for numberOfAggregatedPRB from the range {50, 100, 150, 200, 250, 300, 350, 400};
For numberOfNAICS-CapableCC = 5, UE signals one value for numberOfAggregatedPRB from the range {50, 100, 150, 200, 250, 300, 350, 400, 450, 500}.
-
NonContiguousUL-RA-WithinCC-List
One entry corresponding to each supported E-UTRA band listed in the same order as in supportedBandListEUTRA.
No
noResourceRestrictionForTTIBundling
Indicate wheter the UE supports TTI bundling operation without resource allocation restriction.
-
otdoa-UE-Assisted
Indicates whether the UE supports UE-assisted OTDOA positioning [54].
Yes
pdcp-SN-Extension
Indicates whether the UE supports 15 bit length of PDCP sequence number.
-
pdcp-SN-Extension-18bits
Indicates whether the UE supports 18 bit length of PDCP sequence number.
-
pdcp-TransferSplitUL
Indicates whether the UE supports PDCP data transfer split in UL for the drb-TypeSplit as specified in TS 36.323 [8].
-
phy-TDD-ReConfig-FDD-PCell
Indicates whether the UE supports TDD UL/DL reconfiguration for TDD serving cell(s) via monitoring PDCCH with eIMTA-RNTI on a FDD PCell, and HARQ feedback according to UL and DL HARQ reference configurations. This bit can only be set to supported only if the UE supports FDD PCell and phy-TDD-ReConfig-TDD-PCell is set to supported.
-
phy-TDD-ReConfig-TDD-PCell
Indicates whether the UE supports TDD UL/DL reconfiguration for TDD serving cell(s) via monitoring PDCCH with eIMTA-RNTI on a TDD PCell, and HARQ feedback according to UL and DL HARQ reference configurations, and PUCCH format 3.
-
pmi-Disabling
Yes
powerPrefInd
Indicates whether the UE supports power preference indication.
No
pucch-Format4
Indicates whether the UE supports PUCCH format 4.
-
pucch-Format5
Indicates whether the UE supports PUCCH format 5.
-
pucch-SCell
Indicates whether the UE supports PUCCH on SCell.
-
pusch-FeedbackMode
Indicates whether the UE supports PUSCH feedback mode 3-2.
No
pusch-SRS-PowerControl-SubframeSet
Indicates whether the UE supports subframe set dependent UL power control for PUSCH and SRS. This field is only applicable for UEs supporting TDD.
-
rach-Report
Indicates whether the UE supports delivery of rachReport.
-
requestedBands
Indicates the frequency bands requested by E-UTRAN.
-
requestedMaximumCCs
Indicates whether UE supports reception of requestedMaximumCCsDL and requestedMaximumCCsUL.
-
rsrqMeasWideband
Indicates whether the UE can perform RSRQ measurements with wider bandwidth.
Yes
rsrq-OnAllSymbols
Indicates whether the UE can perform RSRQ measurement on all OFDM symbols and also support the extended RSRQ upper value range from -3dB to 2.5dB in measurement configuration and reporting as specified in TS 36.133 [16].
No
rs-SINR-Meas
Indicates whether the UE can perform RS-SINR measurements in RRC_CONNECTED as specified in TS 36.214 [48].
-
scptm-ParallelReception
Indicates whether the UE in RRC_CONNECTED supports parallel reception in the same subframe of DL-SCH transport blocks transmitted using C-RNTI/Semi-Persistent Scheduling C-RNTI and using SC-RNTI/G-RNTI as specified in TS36.306 [5].
TBD
simultaneousPUCCH-PUSCH
Yes
simultaneousRx-Tx
Indicates whether the UE supports simultaneous reception and transmission on different bands for each band combination listed in supportedBandCombination. This field is only applicable for inter-band TDD band combinations. A UE indicating support of simultaneousRx-Tx and dc-Support-r12 shall support different UL/DL configurations between PCell and PSCell.
-
skipFallbackCombinations
Indicates whether UE supports receiving reception of skipFallbackCombinations that requests UE to exclude fallback band combinations from capability signalling.
-
srvcc-FromUTRA-FDD-ToGERAN
Indicates whether UE supports SRVCC handover from UTRA FDD PS HS to GERAN CS.
-
srvcc-FromUTRA-FDD-ToUTRA-FDD
Indicates whether UE supports SRVCC handover from UTRA FDD PS HS to UTRA FDD CS.
-
srvcc-FromUTRA-TDD128-ToGERAN
Indicates whether UE supports SRVCC handover from UTRA TDD 1.28Mcps PS HS to GERAN CS.
-
srvcc-FromUTRA-TDD128-ToUTRA-TDD128
Indicates whether UE supports SRVCC handover from UTRA TDD 1.28Mcps PS HS to UTRA TDD 1.28Mcps CS.
-
ss-CCH-InterfHandl
Indicates whether the UE supports synchronisation signal and common channel interference handling.
Yes
standaloneGNSS-Location
Indicates whether the UE is equipped with a standalone GNSS receiver that may be used to provide detailed location information in RRC measurement report and logged measurements.
-
supportedBandCombination
Includes the supported CA band combinations, if any, and may include all the supported non-CA bands.
-
supportedBandCombination-r13
Includes the supported CA band combinations, and may include the fallback CA combinations specified in TS 36.101 [42, 4.3A].

supportedBandCombinationAdd-r11
Includes additional supported CA band combinations in case maximum number of CA band combinations of supportedBandCombination is exceeded.
-
SupportedBandCombinationAdd-v11d0, SupportedBandCombinationAdd-v1250, SupportedBandCombinationAdd-v1270
If included, the UE shall include the same number of entries, and listed in the same order, as in SupportedBandCombinationAdd-r11.
-
SupportedBandCombinationExt, SupportedBandCombination-v1090, SupportedBandCombination-v10i0, SupportedBandCombination-v1130, SupportedBandCombination-v1250, SupportedBandCombination-v1270
If included, the UE shall include the same number of entries, and listed in the same order, as in supportedBandCombination-r10.
-
SupportedBandGERAN
GERAN band as defined in TS 45.005 [20].
No
SupportedBandList1XRTT
One entry corresponding to each supported CDMA2000 1xRTT band class.
-
SupportedBandListEUTRA
Includes the supported E-UTRA bands. This field shall include all bands which are indicated in BandCombinationParameters.
-
SupportedBandListEUTRA-v9e0, SupportedBandListEUTRA-v1250
If included, the UE shall include the same number of entries, and listed in the same order, as in supportedBandListEUTRA (i.e. without suffix).
-
SupportedBandListGERAN
No
SupportedBandListHRPD
One entry corresponding to each supported CDMA2000 HRPD band class.
-
SupportedBandUTRA-FDD
UTRA band as defined in TS 25.101 [17].
-
SupportedBandUTRA-TDD128
UTRA band as defined in TS 25.102 [18].
-
SupportedBandUTRA-TDD384
UTRA band as defined in TS 25.102 [18].
-
SupportedBandUTRA-TDD768
UTRA band as defined in TS 25.102 [18].
-
supportedBandwidthCombinationSet
The supportedBandwidthCombinationSet indicated for a band combination is applicable to all bandwidth classes indicated by the UE in this band combination.
Field encoded as a bit map, where bit N is set to "1" if UE support Bandwidth Combination Set N for this band combination, see 36.101 [42]. The leading / leftmost bit (bit 0) corresponds to the Bandwidth Combination Set 0, the next bit corresponds to the Bandwidth Combination Set 1 and so on. The UE shall neither include the field for a non-CA band combination, nor for a CA band combination for which the UE only supports Bandwidth Combination Set 0.
-
supportedBlindDecoding
Number of blind decodes supported per TTI in UE-specific search space as defined in TS 36.306 [5]. Only values 5 to 32 can be used in this version of the specification.
-
supportedCellGrouping
This field indicates for which mapping of serving cells to cell groups (i.e. MCG or SCG) the UE supports asynchronous DC. This field is only present for a band combination with more than two but less than 6 band entries where the UE supports asynchronous DC. If this field is not present but asynchronous operation is supported, the UE supports all possible mappings of serving cells to cell groups for the band combination. The bitmap size is selected based on the number of entries in the combinations, i.e., in case of three entries, the bitmap corresponding to threeEntries is selected and so on.
A bit in the bit string set to 1 indicates that the UE supports asynchronous DC for the cell grouping option represented by the concerned bit position. Each bit position represents a different cell grouping option, as illustrated by a table, see NOTE 5. A cell grouping option is represented by a number of bits, each representing a particular band entry in the band combination with the left-most bit referring to the band listed first in the band combination, etc. Value 0 indicates that the carriers of the corresponding band entry are mapped to a first cell group, while value 1 indicates that the carriers of the corresponding band entry are mapped to a second cell group.
 It is noted that the mapping table does not include entries with all bits set to the same value (0 or 1) as this does not represent a DC scenario (i.e. indicating that the UE supports that all carriers of the corresponding band entry are in one cell group).
-
supportedCSI-Proc
Indicates the maximum number of CSI processes supported on a component carrier within a band. Value n1 corresponds to 1 CSI process, value n3 corresponds to 3 CSI processes, and value n4 corresponds to 4 CSI processes. If this field is included, the UE shall include the same number of entries listed in the same order as in BandParameters. If the UE supports at least 1 CSI process on any component carrier, then the UE shall include this field in all bands in all band combinations.
-
supportedNAICS-2CRS-AP
If included, the UE supports NAICS for the band combination. The UE shall include a bitmap of the same length, and in the same order, as in naics-Capability-List, to indicate 2 CRS AP NAICS capability of the band combination. The first/ leftmost bit points to the first entry of naics-Capability-List, the second bit points to the second entry of naics-Capability-List, and so on.
For band combinations with a single component carrier, UE is only allowed to indicate {numberOfNAICS-CapableCC, numberOfAggregatedPRB} = {1, 100} if NAICS is supported.
-
supportOfLAA
Indicates whether the UE supports LAA operation.
-
supportRohcContextContinue
Indicates whether the UE supports ROHC context continuation operation where the UE does not reset the current ROHC context upon handover.
-
tdd-SpecialSubframe
Indicates whether the UE supports TDD special subframe defined in TS 36.211 [21].
No
tdd-FDD-CA-PCellDuplex
The presence of this field indicates that the UE supports TDD/FDD CA in any supported band combination including at least one FDD band with bandParametersUL and at least one TDD band with bandParametersUL. The first bit is set to "1" if UE supports the TDD PCell. The second bit is set to "1" if UE supports FDD PCell. This field is included only if the UE supports band combination including at least one FDD band with bandParametersUL and at least one TDD band with bandParametersUL. If this field is included, the UE shall set at least one of the bits as "1". If this field is included with DC, then it is applicable within a CG, and the presence of this field indicates the capability of the UE to support TDD/FDD CA with at least one FDD band and at least one TDD band in the same CG, with the value indicating the support for TDD/FDD PCell (PSCell).
-
timerT312
Indicates whether the UE supports T312.
No
tm5-FDD
Indicates whether the UE supports the PDSCH transmission mode 5 in FDD.
-
tm5-TDD
Indicates whether the UE supports the PDSCH transmission mode 5 in TDD.
-
tm9-With-8Tx-FDD
No
twoAntennaPortsForPUCCH
No
txDiv-PUCCH1b-ChSelect
Indicates whether the UE supports transmit diversity for PUCCH format 1b with channel selection.
Yes
ue-Category
UE category as defined in TS 36.306 [5]. Set to values 1 to 12 in this version of the specification.
-
ue-CategoryDL
UE DL category as defined in TS 36.306 [5]. For ASN.1 compatibility, a UE indicating DL category 0 shall also indicate any of the categories (1..5) in ue-Category (without suffix), which is ignored by the eNB. The field ue-CategoryDL is set to values 0, 6, 7, 9 to 17 in this version of the specification.
-
ue-CategoryUL
UE UL category as defined in TS 36.306 [5]. The field ue-CategoryUL-r12 is set to values 0, 3, 5, 7, 8, 13 and 14 in this version of the specification.
-
ue-Rx-TxTimeDiffMeasurements
Indicates whether the UE supports Rx - Tx time difference measurements.
No
ue-SpecificRefSigsSupported
No
ue-SSTD-Meas
Indicates whether the UE supports SSTD measurements between the PCell and the PSCell as specified in TS 36.214 [48].
-
ue-TxAntennaSelectionSupported
TRUE indicates that the UE is capable of supporting UE transmit antenna selection as described in TS 36.213 [23, 8.7].
Yes
ul-CoMP
Indicates whether the UE supports UL Coordinated Multi-Point operation.
No
utran-ProximityIndication
Indicates whether the UE supports proximity indication for UTRAN CSG member cells.
-
ul-64QAM
Indicates whether the UE supports 64QAM in UL on the band. This field is only present when the field ue-CategoryUL is set to 5, 8 or 13.
-
utran-SI-AcquisitionForHO
Indicates whether the UE supports, upon configuration of si-RequestForHO by the network, acquisition and reporting of relevant information using autonomous gaps by reading the SI from a neighbouring UMTS cell.
Yes
voiceOverPS-HS-UTRA-FDD
Indicates whether UE supports IMS voice according to GSMA IR.58 profile in UTRA FDD.
-
voiceOverPS-HS-UTRA-TDD128
Indicates whether UE supports IMS voice in UTRA TDD 1.28Mcps.
-
whiteCellList
Indicates whether the UE supports whiteCellList-r13  to limit the set of cells applicable for measurements.
-
wlan-IW-RAN-Rules
Indicates whether the UE supports RAN-assisted WLAN interworking based on access network selection and traffic steering rules.
-
wlan-IW-ANDSF-Policies
Indicates whether the UE supports RAN-assisted WLAN interworking based on ANDSF policies.
-

NOTE 1:	The IE UE-EUTRA-Capability does not include AS security capability information, since these are the same as the security capabilities that are signalled by NAS. Consequently AS need not provide "man-in-the-middle" protection for the security capabilities.
NOTE 2:	The column FDD/ TDD diff indicates if the UE is allowed to signal, as part of the additional capabilities for an XDD mode i.e. within UE-EUTRA-CapabilityAddXDD-Mode-xNM, a different value compared to the value signalled elsewhere within UE-EUTRA-Capability (i.e. the common value, supported for both XDD modes). A '-' is used to indicate that it is not possible to signal different values (used for fields for which the field description is provided for other reasons). Annex E specifies for which TDD and FDD serving cells a UE supporting TDD/FDD CA shall support a capability for which it indicates support within the capability signalling.
NOTE 3:	All the combinations of CA-MIMO-ParametersUL and CA-MIMO-ParametersDL for one band and across all the bands in each BandCombinationParameters are supported by the UE and have the same measurement gap requirement (i.e. the same BandInfoEUTRA applies). The BandCombinationParameters for the same band combination can be included more than once.
NOTE 4:	UE CA and measurement capabilities indicate the combinations of frequencies that can be configured as serving frequencies.
NOTE 5:	The grouping of the cells to the first and second cell group, as indicated by supportedCellGrouping, is shown in the table below.
Nr of Band Entries:
5
4
3
Length of Bit-String:
15
7
3
Bit String Position
Cell grouping option (0= first cell group, 1= second cell group)
1
00001
0001
001
2
00010
0010
010
3
00011
0011
011
4
00100
0100

5
00101
0101

6
00110
0110

7
00111
0111

8
01000


9
01001


10
01010


11
01011


12
01100


13
01101


14
01110


15
01111




-	UE-RadioPagingInfo
The UE-RadioPagingInfo IE contains information needed for paging of category 0 UE.
UE-RadioPagingInfo information element
-- ASN1START

UE-RadioPagingInfo-r12 ::=				SEQUENCE {
	ue-Category-v1250					INTEGER (0)			OPTIONAL,
	...
}

-- ASN1STOP

-	UE-TimersAndConstants
The IE UE-TimersAndConstants contains timers and constants used by the UE in either RRC_CONNECTED or RRC_IDLE.
UE-TimersAndConstants information element
-- ASN1START

UE-TimersAndConstants ::=			SEQUENCE {
	t300								ENUMERATED {
											ms100, ms200, ms300, ms400, ms600, ms1000, ms1500,
											ms2000},
	t301								ENUMERATED {
											ms100, ms200, ms300, ms400, ms600, ms1000, ms1500,
											ms2000},
	t310								ENUMERATED {
											ms0, ms50, ms100, ms200, ms500, ms1000, ms2000},
	n310								ENUMERATED {
											n1, n2, n3, n4, n6, n8, n10, n20},
	t311								ENUMERATED {
											ms1000, ms3000, ms5000, ms10000, ms15000,
											ms20000, ms30000},
	n311								ENUMERATED {
											n1, n2, n3, n4, n5, n6, n8, n10},
	...
}

-- ASN1STOP

UE-TimersAndConstants field descriptions
n3xy
Constants are described in section 7.4. n1 corresponds with 1, n2 corresponds with 2 and so on.
t3xy
Timers are described in section 7.3. Value ms0 corresponds with 0 ms, ms50 corresponds with 50 ms and so on.

-	VisitedCellInfoList
The IE VisitedCellInfoList includes the mobility history information of maximum of 16 most recently visited cells or time spent outside E-UTRA. The most recently visited cell is stored first in the list. The list includes cells visited in RRC_IDLE and RRC_CONNECTED states.
VisitedCellInfoList information element
-- ASN1START

VisitedCellInfoList-r12 ::=	SEQUENCE (SIZE (1..maxCellHistory-r12)) OF VisitedCellInfo-r12

VisitedCellInfo-r12 ::=				SEQUENCE {
	visitedCellId-r12					CHOICE {
		cellGlobalId-r12						CellGlobalIdEUTRA,
		pci-arfcn-r12							SEQUENCE {
			physCellId-r12							PhysCellId,
			carrierFreq-r12							ARFCN-ValueEUTRA-r9
		}
	}																OPTIONAL,
	timeSpent-r12						INTEGER (0..4095),
	...
}

-- ASN1STOP

VisitedCellInfoList field descriptions
timeSpent
This field indicates the duration of stay in the cell or outside E-UTRA approximated to the closest second. If the duration of stay exceeds 4095s, the UE shall set it to 4095s. 

-	WLAN-OffloadConfig
The IE WLAN-OffloadConfig includes information for traffic steering between E-UTRAN and WLAN. The fields are applicable to both RAN-assisted WLAN interworking based on access network selection and traffic steering rules and RAN-assisted WLAN interworking based on ANDSF policies unless stated otherwise in the field description.
WLAN-OffloadConfig information element
-- ASN1START

WLAN-OffloadConfig-r12 ::= 				SEQUENCE {
	thresholdRSRP-r12						SEQUENCE {
		thresholdRSRP-Low-r12					RSRP-Range,
		thresholdRSRP-High-r12					RSRP-Range
	}																	OPTIONAL, -- Need OR
	thresholdRSRQ-r12						SEQUENCE {
		thresholdRSRQ-Low-r12					RSRQ-Range,
		thresholdRSRQ-High-r12					RSRQ-Range
	}																	OPTIONAL, -- Need OR
	thresholdRSRQ-OnAllSymbolsWithWB-r12	SEQUENCE {
		thresholdRSRQ-OnAllSymbolsWithWB-Low-r12			RSRQ-Range,
		thresholdRSRQ-OnAllSymbolsWithWB-High-r12			RSRQ-Range
	}																	OPTIONAL, -- Need OP
	thresholdRSRQ-OnAllSymbols-r12			SEQUENCE {
			thresholdRSRQ-OnAllSymbolsLow-r12					RSRQ-Range,
			thresholdRSRQ-OnAllSymbolsHigh-r12					RSRQ-Range
	}																	OPTIONAL, -- Need OP
	thresholdRSRQ-WB-r12					SEQUENCE {
		thresholdRSRQ-WB-Low-r12							RSRQ-Range,
		thresholdRSRQ-WB-High-r12							RSRQ-Range
	}																	OPTIONAL, -- Need OP

	thresholdChannelUtilization-r12			SEQUENCE {
		thresholdChannelUtilizationLow-r12		INTEGER (0..255),
		thresholdChannelUtilizationHigh-r12		INTEGER (0..255)
	}																	OPTIONAL, -- Need OR
	thresholdBackhaul-Bandwidth-r12			SEQUENCE {
		thresholdBackhaulDL-BandwidthLow-r12	WLAN-backhaulRate-r12,
		thresholdBackhaulDL-BandwidthHigh-r12	WLAN-backhaulRate-r12,
		thresholdBackhaulUL-BandwidthLow-r12	WLAN-backhaulRate-r12,
	 	thresholdBackhaulUL-BandwidthHigh-r12	WLAN-backhaulRate-r12
	}																	OPTIONAL, -- Need OR
	thresholdBeaconRSSI-r12						SEQUENCE {
		thresholdBeaconRSSI-Low-r12					INTEGER (0..255),
		thresholdBeaconRSSI-High-r12					INTEGER (0..255)
	}																	OPTIONAL, -- Need OR
	offloadPreferenceIndicator-r12			BIT STRING (SIZE (16))		OPTIONAL, -- Need OR
	t-SteeringWLAN-r12						T-Reselection				OPTIONAL, -- Need OR
	...
}

WLAN-backhaulRate-r12 ::=					ENUMERATED
										 {r0, r4, r8, r16, r32, r64, r128, r256, r512,
										 r1024, r2048, r4096, r8192, r16384, r32768, r65536, r131072,
										 r262144, r524288, r1048576, r2097152, r4194304, r8388608,
										 r16777216, r33554432, r67108864, r134217728, r268435456,
										 r536870912, r1073741824, r2147483648, r4294967296}

-- ASN1STOP

WLAN-OffloadConfig field descriptions
offloadPreferenceIndicator
Indicates the offload preference indicator. Parameter: OPI in TS 24.312 [66]. Only applicable to RAN-assisted WLAN interworking based on ANDSF policies.
thresholdBackhaulDLBandwidth-High
Indicates the backhaul available downlink bandwidth threshold used by the UE for traffic steering to WLAN. Parameter: ThreshBackhRateDLWLAN, High in TS 36.304 [4]. Value in kilobits/second. Value rN corresponds to N kbps.
thresholdBackhaulDLBandwidth-Low
Indicates the backhaul available downlink bandwidth threshold used by the UE for traffic steering to E-UTRAN. Parameter: ThreshBackhRateDLWLAN, Low in TS 36.304 [4]. Value in kilobits/second. Value rN corresponds to N kbps.
thresholdBackhaulULBandwidth-High
Indicates the backhaul available uplink bandwidth threshold used by the UE for traffic steering to WLAN. Parameter: ThreshBackhRateULWLAN, High in TS 36.304 [4]. Value in kilobits/second. Value rN corresponds to N kbps.
thresholdBackhaulULBandwidth-Low
Indicates the backhaul available uplink bandwidth threshold used by the UE for traffic steering to E-UTRAN. Parameter: ThreshBackhRateULWLAN, Low in TS 36.304 [4]. Value in kilobits/second. Value rN corresponds to N kbps.
thresholdBeaconRSSI-High
Indicates the Beacon RSSI threshold used by the UE for traffic steering to WLAN. Parameter: ThreshBeaconRSSIWLAN, High in TS 36.304 [4]. Value 0 corresponds to -128dBm, 1 corresponds to -127dBm and so on.
thresholdBeaconRSSI-Low
Indicates the Beacon RSSI threshold used by the UE for traffic steering to E-UTRAN. Parameter: ThreshBeaconRSSIWLAN, Low in TS 36.304 [4]. Value 0 corresponds to -128dBm, 1 corresponds to -127dBm and so on.
thresholdChannelUtilization-High
Indicates the WLAN channel utilization (BSS load) threshold used by the UE for traffic steering to E-UTRAN. Parameter: ThreshChUtilWLAN, High in TS 36.304 [4].
thresholdChannelUtilization-Low
Indicates the WLAN channel utilization (BSS load) threshold used by the UE for traffic steering to WLAN. Parameter: ThreshChUtilWLAN, Low in TS 36.304 [4].
thresholdRSRP-High
Indicates the RSRP threshold (in dBm) used by the UE for traffic steering to E-UTRAN. Parameter: ThreshServingOffloadWLAN, HighP in TS 36.304 [4].
thresholdRSRP-Low
Indicates the RSRP threshold (in dBm) used by the UE for traffic steering to WLAN. Parameter: ThreshServingOffloadWLAN, LowP in TS 36.304 [4].
thresholdRSRQ-High,thresholdRSRQ-OnAllSymbolsHigh, thresholdRSRQ-WB-High, thresholdRSRQ-OnAllSymbolsWithWB-High
Indicates the RSRQ threshold (in dB) used by the UE for traffic steering to E-UTRAN. Parameter: ThreshServingOffloadWLAN, HighQ in TS 36.304 [4]. The UE shall only apply one of threshold values of thresholdRSRQ-OnAllSymbolsWithWB-High, thresholdRSRQ-OnAllSymbolsHigh, thresholdRSRQ-WB-High and thresholdRSRQ-High as present in wlan-OffloadConfigCommon and forward this to upper layer. NOTE 1.
thresholdRSRQ-Low,thresholdRSRQ-OnAllSymbolsLow, thresholdRSRQ-WB-Low, thresholdRSRQ-OnAllSymbolsWithWB-Low
Indicates the RSRQ threshold (in dB) used by the UE for traffic steering to WLAN. Parameter: ThreshServingOffloadWLAN, LowQ in TS 36.304 [4].
The UE shall only apply one of threshold values of thresholdRSRQ-OnAllSymbolsWithWB-Low, thresholdRSRQ-OnAllSymbolsLow, thresholdRSRQ-WB-Low and thresholdRSRQ-Low as present in wlan-OffloadConfigCommon and forward this to upper layer. NOTE 1.
t-SteeringWLAN
Indicates the timer value during which the rules should be fulfilled before starting traffic steering between E-UTRAN and WLAN. Parameter: TsteeringWLAN in TS 36.304 [4]. Only applicable to RAN-assisted WLAN interworking based on access network selection and traffic steering rules.

NOTE 1:	Within SIB17, E-UTRAN includes the fields corresponding to same RSRQ types as included in SIB1. E.g. if E-UTRAN includes q-QualMinRSRQ-OnAllSymbols in SIB1 it also includes thresholdRSRQ-OnAllSymbols in SIB17. Within the RRCConnectionReconfiguration message E-UTRAN only includes thresholdRSRQ, setting the value according to the RSRQ type used for E-UTRAN. The UE shall apply the RSRQ fields (RSRQ threshold, high and low) corresponding to one RSRQ type i.e. the same as it applies for E-UTRAN.


6.3.7	MBMS information elements

-	MBMS-NotificationConfig
The IE MBMS-NotificationConfig specifies the MBMS notification related configuration parameters, that are applicable for all MBSFN areas.
MBMS-NotificationConfig information element
-- ASN1START

MBMS-NotificationConfig-r9 ::=				SEQUENCE {
	notificationRepetitionCoeff-r9		ENUMERATED {n2, n4},
	notificationOffset-r9				INTEGER (0..10),
	notificationSF-Index-r9				INTEGER (1..6)
}

-- ASN1STOP

MBMS-NotificationConfig field descriptions
notificationOffset
Indicates, together with the notificationRepetitionCoeff, the radio frames in which the MCCH information change notification is scheduled i.e. the MCCH information change notification is scheduled in radio frames for which: SFN mod notification repetition period = notificationOffset.
notificationRepetitionCoeff
Actual change notification repetition period common for all MCCHs that are configured= shortest modification period/ notificationRepetitionCoeff. The 'shortest modificaton period' corresponds with the lowest value of mcch-ModificationPeriod of all MCCHs that are configured. Value n2 corresponds to coefficient 2, and so on.
notificationSF-Index
Indicates the subframe used to transmit MCCH change notifications on PDCCH.
FDD: Value 1, 2, 3, 4, 5 and 6 correspond with subframe #1, #2, #3 #6, #7, and #8 respectively.
TDD: Value 1, 2, 3, 4, and 5 correspond with subframe #3, #4, #7, #8, and #9 respectively.

-	MBMSServiceList
The IE MBMSServiceList provides the list of MBMS services which the UE is receiving or interested to receive.
MBMSServiceList information element
-- ASN1START

MBMSServiceList-r13 ::=			SEQUENCE (SIZE (0..maxMBMSServiceListPerUE-r13)) OF MBMSServiceInfo-r13

MBMSServiceInfo-r13 ::= 				SEQUENCE	{
	tmgi-r13							TMGI-r9
}

-- ASN1STOP

-	MBSFN-AreaId
The IE MBSFN-AreaId identifies an MBSFN area by means of a locally unique value at lower layers i.e. it concerns parameter NIDMBSFN in TS 36.211 [21, 6.10.2.1].
MBSFN-AreaId information element
-- ASN1START

MBSFN-AreaId-r12 ::=					INTEGER (0..255)

-- ASN1STOP

-	MBSFN-AreaInfoList
The IE MBSFN-AreaInfoList contains the information required to acquire the MBMS control information associated with one or more MBSFN areas.
MBSFN-AreaInfoList information element
-- ASN1START

MBSFN-AreaInfoList-r9 ::=			SEQUENCE (SIZE(1..maxMBSFN-Area)) OF MBSFN-AreaInfo-r9

MBSFN-AreaInfo-r9 ::=				SEQUENCE {
	mbsfn-AreaId-r9						MBSFN-AreaId-r12,
	non-MBSFNregionLength				ENUMERATED {s1, s2},
	notificationIndicator-r9				INTEGER (0..7),
	mcch-Config-r9						SEQUENCE {
		mcch-RepetitionPeriod-r9			ENUMERATED {rf32, rf64, rf128, rf256},
		mcch-Offset-r9						INTEGER (0..10),
		mcch-ModificationPeriod-r9			ENUMERATED {rf512, rf1024},
		sf-AllocInfo-r9						BIT STRING (SIZE(6)),
		signallingMCS-r9					ENUMERATED {n2, n7, n13, n19}
	},
	...
}

-- ASN1STOP

MBSFN-AreaInfoList field descriptions
mcch-ModificationPeriod
Defines periodically appearing boundaries, i.e. radio frames for which SFN mod mcch-ModificationPeriod = 0. The contents of different transmissions of MCCH information can only be different if there is at least one such boundary in-between them.
mcch-Offset
Indicates, together with the mcch-RepetitionPeriod, the radio frames in which MCCH is scheduled i.e. MCCH is scheduled in radio frames for which: SFN mod mcch-RepetitionPeriod = mcch-Offset.
mcch-RepetitionPeriod
Defines the interval between transmissions of MCCH information, in radio frames, Value rf32 corresponds to 32 radio frames, rf64 corresponds to 64 radio frames and so on.
non-MBSFNregionLength
Indicates how many symbols from the beginning of the subframe constitute the non-MBSFN region. This value applies in all subframes of the MBSFN area used for PMCH transmissions as indicated in the MSI. The values s1 and s2 correspond with 1 and 2 symbols, respectively: see TS 36.211 [21, Table 6.7-1].
notificationIndicator
Indicates which PDCCH bit is used to notify the UE about change of the MCCH applicable for this MBSFN area. Value 0 corresponds with the least significant bit as defined in TS 36.212 [22, Section 5.3.3.1] and so on.
sf-AllocInfo
Indicates the subframes of the radio frames indicated by the mcch-RepetitionPeriod and the mcch-Offset, that may carry MCCH. Value "1" indicates that the corresponding subframe is allocated. The following mapping applies:
FDD: The first/ leftmost bit defines the allocation for subframe #1 of the radio frame indicated by mcch-RepetitionPeriod and mcch-Offset, the second bit for #2, the third bit for #3 , the fourth bit for #6, the fifth bit for #7 and the sixth bit for #8.
TDD: The first/leftmost bit defines the allocation for subframe #3 of the radio frame indicated by mcch-RepetitionPeriod and mcch-Offset, the second bit for #4, third bit for #7, fourth bit for #8, fifth bit for #9. Uplink subframes are not allocated. The last bit is not used.
signallingMCS
Indicates the Modulation and Coding Scheme (MCS) applicable for the subframes indicated by the field sf-AllocInfo and for each (P)MCH that is configured for this MBSFN area, for the first subframe allocated to the (P)MCH within each MCH scheduling period (which may contain the MCH scheduling information provided by MAC). Value n2 corresponds with the value 2 for parameter in TS 36.213 [23, Table 7.1.7.1-1], and so on.

-	MBSFN-SubframeConfig
The IE MBSFN-SubframeConfig defines subframes that are reserved for MBSFN in downlink.
MBSFN-SubframeConfig information element
-- ASN1START

MBSFN-SubframeConfig ::=			SEQUENCE {
	radioframeAllocationPeriod			ENUMERATED {n1, n2, n4, n8, n16, n32},
	radioframeAllocationOffset			INTEGER (0..7),
	subframeAllocation					CHOICE {
		oneFrame							BIT STRING (SIZE(6)),
		fourFrames							BIT STRING (SIZE(24))
	}
}
-- ASN1STOP

MBSFN-SubframeConfig field descriptions
fourFrames
A bit-map indicating MBSFN subframe allocation in four consecutive radio frames, "1" denotes that the corresponding subframe is allocated for MBSFN. The bitmap is interpreted as follows:
FDD: Starting from the first radioframe and from the first/leftmost bit in the bitmap, the allocation applies to subframes #1, #2, #3 , #6, #7, and #8 in the sequence of the four radio-frames.
TDD: Starting from the first radioframe and from the first/leftmost bit in the bitmap, the allocation applies to subframes #3, #4, #7, #8, and #9 in the sequence of the four radio-frames. The last four bits are not used. E-UTRAN allocates uplink subframes only if eimta-MainConfig is configured.
oneFrame
"1" denotes that the corresponding subframe is allocated for MBSFN. The following mapping applies:
FDD: The first/leftmost bit defines the MBSFN allocation for subframe #1, the second bit for #2, third bit for #3 , fourth bit for #6, fifth bit for #7, sixth bit for #8.
TDD: The first/leftmost bit defines the allocation for subframe #3, the second bit for #4, third bit for #7, fourth bit for #8, fifth bit for #9. E-UTRAN allocates uplink subframes only if eimta-MainConfig is configured. The last bit is not used.
radioFrameAllocationPeriod, radioFrameAllocationOffset
Radio-frames that contain MBSFN subframes occur when equation SFN mod radioFrameAllocationPeriod = radioFrameAllocationOffset is satisfied. Value n1 for radioframeAllocationPeriod denotes value 1, n2 denotes value 2, and so on. When fourFrames is used for subframeAllocation, the equation defines the first radio frame referred to in the description below. Values n1 and n2 are not applicable when fourFrames is used.
subframeAllocation
Defines the subframes that are allocated for MBSFN within the radio frame allocation period defined by the radioFrameAllocationPeriod and the radioFrameAllocationOffset.

-	PMCH-InfoList
The IE PMCH-InfoList specifies configuration of all PMCHs of an MBSFN area, while IE PMCH-InfoListExt includes additional PMCHs, i.e. extends the PMCH list using the general principles specified in 5.1.2. The information provided for an individual PMCH includes the configuration parameters of the sessions that are carried by the concerned PMCH. For all PMCH that E-UTRAN includes in PMCH-InfoList, the list of ongoing sessions has at least one entry.
PMCH-InfoList information element
-- ASN1START

PMCH-InfoList-r9 ::=				SEQUENCE (SIZE (0..maxPMCH-PerMBSFN)) OF PMCH-Info-r9

PMCH-InfoListExt-r12 ::=			SEQUENCE (SIZE (0..maxPMCH-PerMBSFN)) OF PMCH-InfoExt-r12

PMCH-Info-r9 ::=					SEQUENCE {
	pmch-Config-r9						PMCH-Config-r9,
	mbms-SessionInfoList-r9			MBMS-SessionInfoList-r9,
	...
}

PMCH-InfoExt-r12 ::=				SEQUENCE {
	pmch-Config-r12						PMCH-Config-r12,
	mbms-SessionInfoList-r12			MBMS-SessionInfoList-r9,
	...
}

MBMS-SessionInfoList-r9 ::=		SEQUENCE (SIZE (0..maxSessionPerPMCH)) OF MBMS-SessionInfo-r9

MBMS-SessionInfo-r9 ::=			SEQUENCE {
	tmgi-r9								TMGI-r9,
	sessionId-r9						OCTET STRING (SIZE (1)) 		OPTIONAL, 	-- Need OR
	logicalChannelIdentity-r9			INTEGER (0..maxSessionPerPMCH-1),
	...
}

PMCH-Config-r9 ::=					SEQUENCE {
	sf-AllocEnd-r9						INTEGER (0..1535),
	dataMCS-r9							INTEGER (0..28),
	mch-SchedulingPeriod-r9			ENUMERATED {
										rf8, rf16, rf32, rf64, rf128, rf256, rf512, rf1024},
	...
}

PMCH-Config-r12 ::=					SEQUENCE {
	sf-AllocEnd-r12						INTEGER (0..1535),
	dataMCS-r12							CHOICE {
		normal-r12							INTEGER (0..28),
		higerOrder-r12						INTEGER (0..27)
	},
	mch-SchedulingPeriod-r12		ENUMERATED {
										rf4, rf8, rf16, rf32, rf64, rf128, rf256, rf512, rf1024},
	...
}

TMGI-r9 ::=						SEQUENCE {
	plmn-Id-r9							CHOICE {
		plmn-Index-r9						INTEGER (1..maxPLMN-r11),
		explicitValue-r9					PLMN-Identity
	},
	serviceId-r9						OCTET STRING (SIZE (3))
}


-- ASN1STOP

PMCH-InfoList field descriptions
dataMCS
Indicates the value for parameter in TS 36.213 [23], which defines the Modulation and Coding Scheme (MCS) applicable for the subframes of this (P)MCH as indicated by the field commonSF-Alloc. Value normal corresponds to Table 7.1.7.1-1 and value higherOrder corresponds to Table 7.1.7.1-1A. The MCS does however neither apply to the subframes that may carry MCCH i.e. the subframes indicated by the field sf-AllocInfo within SystemInformationBlockType13 nor for the first subframe allocated to this (P)MCH within each MCH scheduling period (which may contain the MCH scheduling information provided by MAC). 
mch-SchedulingPeriod
Indicates the MCH scheduling period i.e. the periodicity used for providing MCH scheduling information at lower layers (MAC) applicable for an MCH. Value rf8 corresponds to 8 radio frames, rf16 corresponds to 16 radio frames and so on. The mch-SchedulingPeriod starts in the radio frames for which: SFN mod mch-SchedulingPeriod = 0. E-UTRAN configures mch-SchedulingPeriod of the (P)MCH listed first in PMCH-InfoList to be smaller than or equal to mcch-RepetitionPeriod.
plmn-Index
Index of the entry in field plmn-IdentityList within SystemInformationBlockType1.
sessionId
Indicates the optional MBMS Session Identity, which together with TMGI identifies a transmission or a possible retransmission of a specific MBMS session: see TS 29.061 [51, Sections 20.5, 17.7.11, 17.7.15]. The field is included whenever upper layers have assigned a session identity i.e. one is available for the MBMS session in E-UTRAN.
serviceId
Uniquely identifies the identity of an MBMS service within a PLMN. The field contains octet 3- 5 of the IE Temporary Mobile Group Identity (TMGI) as defined in TS 24.008 [49]. The first octet contains the third octet of the TMGI, the second octet contains the fourth octet of the TMGI and so on.
sf-AllocEnd
Indicates the last subframe allocated to this (P)MCH within a period identified by field commonSF-AllocPeriod. The subframes allocated to (P)MCH corresponding with the nth entry in pmch-InfoList are the subsequent subframes starting from either the next subframe after the subframe identified by sf-AllocEnd of the (n-1)th listed (P)MCH or, for n=1, the first subframe defined by field commonSF-Alloc, through the subframe identified by sf-AllocEnd of the nth listed (P)MCH. Value 0 corresponds with the first subframe defined by field commonSF-Alloc. 

6.3.7a	SC-PTM information elements
-	SC-MTCH-InfoList
The IE SC-MTCH-InfoList provides the list of ongoing MBMS sessions transmitted via SC-MRB and for each MBMS session, the associated G-RNTI and scheduling information.
SC-MTCH-InfoList information element
-- ASN1START

SC-MTCH-InfoList-r13 ::=			SEQUENCE (SIZE (0..maxSC-MTCH-r13)) OF SC-MTCH-Info-r13

SC-MTCH-Info-r13 ::= 				SEQUENCE	{
	mbmsSessionInfo-r13						MBMSSessionInfo-r13,
	g-RNTI-r13								C-RNTI,
	sc-mtch-schedulingInfo-r13				SC-MTCH-SchedulingInfo-r13			OPTIONAL,
	sc-mtch-neighbourCell-r13				BIT STRING (SIZE(maxNeighCellSCPTM-r13))	OPTIONAL,
	...
}

MBMSSessionInfo-r13 ::=				SEQUENCE	{
	tmgi-r13								TMGI-r9,
	sessionId-r13							OCTET STRING (SIZE (1))		OPTIONAL 	-- Need OR
}

SC-MTCH-SchedulingInfo-r13::=		SEQUENCE	{
	onDurationTimerSCPTM-r13				ENUMERATED {
												psf1, psf2, psf3, psf4, psf5, psf6,
												psf8, psf10, psf20, psf30, psf40,
												psf50, psf60, psf80, psf100,
												psf200},
	drx-InactivityTimerSCPTM-r13			ENUMERATED {
												psf0, psf1, psf2, psf4, psf8,
												psf10, psf20, psf40,
												psf80, psf160, ps320,
												psf640, psf960,
												psf1280, psf1920, psf2560},
	schedulingPeriodStartOffsetSCPTM-r13	CHOICE {
		sf10									INTEGER(0..9),
		sf20									INTEGER(0..19),
		sf32									INTEGER(0..31),
		sf40									INTEGER(0..39),
		sf64									INTEGER(0..63),
		sf80									INTEGER(0..79),
		sf128									INTEGER(0..127),
		sf160									INTEGER(0..159),
		sf256									INTEGER(0..255),
		sf320									INTEGER(0..319),
		sf512									INTEGER(0..511),
		sf640									INTEGER(0..639),
		sf1024									INTEGER(0..1023)
	},
	...
}

-- ASN1STOP

SC-MTCH-InfoList field descriptions
mbmsSessionInfo
Indicates the ongoing MBMS session in a SC-MTCH.
g-RNTI
G-RNTI used to scramble the scheduling and transmission of a SC-MTCH.
sc-mtch-schedulingInfo
DRX information for the SC-MTCH. If this field absent, the SC-MTCH may be scheduled in any subframe.
onDurationTimerSCPTM
Timer for SC-MTCH reception in TS 36.321 [6]. Value in number of PDCCH sub-frames. Value psf1 corresponds to 1 PDCCH sub-frame, psf2 corresponds to 2 PDCCH sub-frames and so on.
drx-InactivityTimerSCPTM
Timer for SC-MTCH in TS 36.321 [6]. Value in number of PDCCH sub-frames. Value psf0 corresponds to timer not configured, psf1 corresponds to 1 PDCCH sub-frame, psf2 corresponds to 2 PDCCH sub-frames and so on.
schedulingPeriodStartOffsetSCPTM
SC-MTCH-SchedulingCycle and SC-MTCH-SchedulingOffset in TS 36.321 [6]. The value of SC-MTCH-SchedulingCycle is in number of sub-frames. Value sf10 corresponds to 10 sub-frames, sf20 corresponds to 20 sub-frames and so on.
sc-mtch-neighbourCell
Indicates neighbour cells which also provide this service on SC-MTCH. The first bit is set to 1 if the service is provided on SC-MTCH in the first cell in scptmNeighbourCellList, otherwise it is set to 0. The second bit is set to 1 if the service is provided on SC-MTCH in the second cell in scptmNeighbourCellList, and so on. If this field is absent, this service is not available on SC-MTCH in any neighbour cell.

-	SCPTMNeighbourCellList
The IE SCPTMNeighbourCellList indicates a list of neighbour cells where ongoing MBMS sessions provided via SC-MRB in the current cells are also provided.

-- ASN1START

SCPTMNeighbourCellList-r13 ::=		SEQUENCE (SIZE (1..maxNeighCellSCPTM-r13)) OF CellIdentity

-- ASN1STOP

6.3.8	Sidelink information elements
-	SL-CommConfig
The IE SL-CommConfig specifies the dedicated configuration information for sidelink communication. In particular it concerns the transmission resource configuration for sidelink communication on the primary frequency.
SL-CommConfig information element
-- ASN1START

SL-CommConfig-r12 ::= 				SEQUENCE	{
	commTxResources-r12					CHOICE {
		release								NULL,
		setup								CHOICE {
			scheduled-r12					SEQUENCE {
				sl-RNTI-r12						C-RNTI,
				mac-MainConfig-r12				MAC-MainConfigSL-r12,
				sc-CommTxConfig-r12				SL-CommResourcePool-r12,
				mcs-r12							INTEGER (0..28) 				OPTIONAL	-- Need OP
			},
			ue-Selected-r12					SEQUENCE {
				-- Pool for normal usage
				commTxPoolNormalDedicated-r12	SEQUENCE {
					poolToReleaseList-r12			SL-TxPoolToReleaseList-r12 OPTIONAL,	-- Need ON
					poolToAddModList-r12			SL-CommTxPoolToAddModList-r12 OPTIONAL	-- Need ON
				}
			}
		}
	}																		OPTIONAL,	-- Need ON
	...,
	[[	scheduled-r13x0						CHOICE {
			release								NULL,
			setup								SEQUENCE {
				logicalChGroupInfoList-r13			LogicalChGroupInfoList-r13,
				multipleTxAllowed-r13				BOOLEAN
			}
		}																	OPTIONAL,	-- Need ON
		ue-Selected-r13x0					SEQUENCE {
			commTxPoolNormalDedicatedExt-r13	SEQUENCE {
				poolToReleaseListExt-r13			SL-TxPoolToReleaseListExt-r13 OPTIONAL,	-- Need ON
				poolToAddModListExt-r13				SL-CommTxPoolToAddModListExt-r13	OPTIONAL	-- Need ON
			}
		}																OPTIONAL,	-- Need ON
		commTxAllowRelayDedicated-r13		BOOLEAN			OPTIONAL	-- Need ON
	]]}

LogicalChGroupInfoList-r13 ::=		SEQUENCE (SIZE (1..maxLCG-r13)) OF SL-PriorityList-r13

SL-CommTxPoolToAddModList-r12 ::=		SEQUENCE (SIZE (1..maxSL-TxPool-r12)) OF SL-CommTxPoolToAddMod-r12

SL-CommTxPoolToAddModListExt-r13 ::=	SEQUENCE (SIZE (1..maxSL-CommTxPool-v13x0)) OF SL-CommTxPoolToAddModExt-r13

SL-CommTxPoolToAddMod-r12 ::=		SEQUENCE	{
	poolIdentity-r12					SL-TxPoolIdentity-r12,
	pool-r12							SL-CommResourcePool-r12
}

SL-CommTxPoolToAddModExt-r13 ::=		SEQUENCE	{
	poolIdentity-v13x0					SL-CommTxPoolIdentity-v13x0,
	pool-r13							SL-CommResourcePool-r12
}

MAC-MainConfigSL-r12 ::= 		SEQUENCE	{
	periodic-BSR-TimerSL					PeriodicBSR-Timer-r12 		OPTIONAL, 	-- Need ON
	retx-BSR-TimerSL						RetxBSR-Timer-r12
}

-- ASN1STOP

SL-CommConfig field descriptions
commTxAllowRelayDedicated
Indicates for whether the UE is not allowed to transmit relay related data using the configured dedicated transmission resources i.e. neither via scheduled nor via UE selected resources.
commTxPoolNormalDedicated
Indicates a pool of transmission resources the UE is allowed to use while in RRC_CONNECTED.
logicalChGroupInfoList
Indicates for each logical channel group the list of associated priorities, used as specified in TS 36.321 [6].
mcs
Indicates the Modulation and Coding Scheme as defined in TS 36.212 [23, 14.2.1]. If not configured, the selection of Modulation and Coding Scheme is up to UE implementation.
multipleTxAllowed
Indicates whether or not multiple transmissions in one SC period is allowed.
sc-CommTxConfig
Indicates a pool of resources for SC when E-UTRAN schedules Tx resources (i.e. when indices included in DCI format 5 indicate the actual data resources to be used as specified in TS 36.212 [22, 5.3.3.1.9]).
scheduled
Indicates the configuration for the case E-UTRAN schedules the transmission resources based on sidelink specific BSR from the UE.
ue-Selected
Indicates the configuration for the case the UE selects the transmission resources from a pool of resources configured by E-UTRAN.

-	SL-CommResourcePool
The IE SL-CommResourcePool specifies the configuration information for an individual pool of resources for sidelink communication. The IE covers the configuration of both the sidelink control information and the data.
SL-CommResourcePool information element
-- ASN1START

SL-CommTxPoolList-r12 ::=		SEQUENCE (SIZE (1..maxSL-TxPool-r12)) OF SL-CommResourcePool-r12

SL-CommTxPoolListExt-r13 ::=	SEQUENCE (SIZE (1..maxSL-CommTxPool-v13x0)) OF SL-CommResourcePool-r12

SL-CommRxPoolList-r12 ::=		SEQUENCE (SIZE (1..maxSL-RxPool-r12)) OF SL-CommResourcePool-r12

SL-CommResourcePool-r12 ::=		SEQUENCE {
	sc-CP-Len-r12						SL-CP-Len-r12,
	sc-Period-r12						SL-PeriodComm-r12,
	sc-TF-ResourceConfig-r12			SL-TF-ResourceConfig-r12,
	data-CP-Len-r12						SL-CP-Len-r12,
	dataHoppingConfig-r12				SL-HoppingConfigComm-r12,
	ue-SelectedResourceConfig-r12			SEQUENCE {
		data-TF-ResourceConfig-r12				SL-TF-ResourceConfig-r12,
		trpt-Subset-r12						SL-TRPT-Subset-r12 	OPTIONAL	-- Need OP
	}																OPTIONAL, 	-- Need OR
	rxParametersNCell-r12				SEQUENCE {
		tdd-Config-r12					TDD-Config					OPTIONAL, 	-- Need OP
		syncConfigIndex-r12			INTEGER (0..15)
	} 																OPTIONAL, 	-- Need OR
	txParameters-r12					SEQUENCE {
		sc-TxParameters-r12				SL-TxParameters-r12,
		dataTxParameters-r12			SL-TxParameters-r12
	} 																OPTIONAL, 	-- Cond Tx
	...,
	[[	priorityList-r13				SL-PriorityList-r13			OPTIONAL 	-- Cond Tx
	]]

}

SL-TRPT-Subset-r12 ::=			BIT STRING (SIZE (3..5))

-- ASN1STOP

SL-CommResourcePool field descriptions
sc-Period
Indicates the period over which resources are allocated in a cell for SC and over which scheduled and UE selected data transmissions occur, see PSCCH period in TS 36.213 [23]. Value in number of subframes. Value sf40 corresponds to 40 subframes, sf80 corresponds to 80 subframes and so on. E-UTRAN configures values sf40, sf80, sf160 and sf320 for FDD and for TDD config 1 to 5, values sf70, sf140 and sf280 for TDD config 0, and finally values sf60, sf120 and sf240 for TDD config 6.
syncConfigIndex
Indicates the synchronisation configuration that is associated with a reception pool, by means of an index to the corresponding entry of commSyncConfig in SystemInformationBlockType18.
tdd-Config
TDD configuration associated with the reception pool of the cell indicated by syncConfigIndex. Absence of the field indicates the same duplex mode as the cell providing this field and the same UL/DL configuration as indicated by subframeAssignment in SystemInformationBlockType1 in case of TDD. 
trpt-Subset
Indicates the subset of T-RPT available (see TS 36.213 [23, 14.1.1.1.1]). Consists of a bitmap which is used to indicate the set of available 'k' values to be used for sidelink communication (see TS 36.213 [23, 14.1.1.3]). If T-RPT subset configuration is not signaled/ preconfigured then UE assumes the whole T-RPT set is available.

Conditional presence
Explanation
Tx
The field is mandatory present when included in commTxPoolNormalDedicated, commTxPoolNormalCommon or commTxPoolExceptional. Otherwise the field is not present.

-	SL-CP-Len
The IE SL-CP-Len indicates the cyclic prefix length, see TS 36.211 [21].
SL-CP-Len information element
-- ASN1START

SL-CP-Len-r12 ::=				ENUMERATED {normal, extended}

-- ASN1STOP

-	SL-DiscConfig
The IE SL-DiscConfig specifies the dedicated configuration information for sidelink discovery.
SL-DiscConfig information element
-- ASN1START

SL-DiscConfig-r12 ::=					SEQUENCE {
	discTxResources-r12						CHOICE {
		release								NULL,
		setup								CHOICE {
			scheduled-r12					SEQUENCE {
				discTxConfig-r12					SL-DiscResourcePool-r12	OPTIONAL, -- Need ON
				discTF-IndexList-r12				SL-TF-IndexPairList-r12 	OPTIONAL, -- Need ON
				discHoppingConfig-r12				SL-HoppingConfigDisc-r12
														OPTIONAL	-- Need ON
			},
			ue-Selected-r12					SEQUENCE {
				discTxPoolDedicated-r12			SEQUENCE {
					poolToReleaseList-r12			SL-TxPoolToReleaseList-r12 OPTIONAL,	-- Need ON
					poolToAddModList-r12			SL-DiscTxPoolToAddModList-r12 OPTIONAL	-- Need ON
				} 													OPTIONAL	-- Need ON
			}
		}
	}																OPTIONAL,	-- Need ON
	...,
	[[	discTF-IndexList-v1260				CHOICE {
			release								NULL,
			setup								SEQUENCE {
				discTF-IndexList-r12b				SL-TF-IndexPairList-r12b
			}
		}															OPTIONAL	-- Need ON
	]],
	[[	discTxResourcesPS-r13			CHOICE {
			release								NULL,
			setup								CHOICE {
				scheduled-r13						SL-DiscTxConfigScheduled-r13,
				ue-Selected-r13						SEQUENCE {
					discTxPoolPS-Dedicated-r13			SL-DiscTxPoolDedicated-r13
				}
			}
		}															OPTIONAL,	-- Need ON
		discTxInterFreqInfo-r13			CHOICE {
			release								NULL,
			setup								SEQUENCE {
				discTxCarrierFreq-r13				ARFCN-ValueEUTRA-r9			OPTIONAL,	-- Need OR
				discTxRefCarrierDedicated-r13		SL-DiscTxRefCarrierDedicated-r13	OPTIONAL,	-- Need OR
				discTxInfoInterFreqListExt-r13			SL-DiscTxInfoInterFreqListExt-r13	OPTIONAL	-- Need ON
			}
		}															OPTIONAL,	-- Need ON
		gapRequestsAllowedDedicated-r13		ENUMERATED {false, true}	OPTIONAL,	-- Need ON
		discRxGapConfig-r13					CHOICE {
			release								NULL,
			setup								SL-GapConfig-r13
		}															OPTIONAL,	-- Need ON
		discTxGapConfig-r13					CHOICE {
			release								NULL,
			setup								SL-GapConfig-r13
		}															OPTIONAL,	-- Need ON
		discSysInfoReportConfig-r13			CHOICE {
			release								NULL,
			setup								SL-DiscSysInfoReportFreqList-r13
		}															OPTIONAL	-- Need ON
	]]
}

SL-DiscSysInfoReportFreqList-r13 ::= SEQUENCE (SIZE (1..maxFreq)) OF ARFCN-ValueEUTRA-r9

SL-DiscTxInfoInterFreqListExt-r13 ::=	SEQUENCE {
	discTxFreqToAddModList-r13				SEQUENCE (SIZE (1..maxFreq)) OF SL-DiscTxResourceInfoPerFreq-r13	OPTIONAL,	-- Need ON
	discTxFreqToReleaseList-r13				SEQUENCE (SIZE (1..maxFreq)) OF ARFCN-ValueEUTRA-r9	OPTIONAL	-- Need ON
}

SL-DiscTxResourceInfoPerFreq-r13 ::=	SEQUENCE	{
	discTxCarrierFreq-r13					ARFCN-ValueEUTRA-r9,
	discTxResources-r13						SL-DiscTxResource-r13	OPTIONAL,	-- Need OR
	discTxResourcesPS-r13					SL-DiscTxResource-r13	OPTIONAL,	-- Need OR
	discTxRefCarrierDedicated-r13			SL-DiscTxRefCarrierDedicated-r13	OPTIONAL,	-- Need OR
	cellSelectionInfo-r13					CellSelectionInfoNFreq-r13			OPTIONAL	-- Need OR
}

SL-DiscTxResource-r13 ::=				CHOICE {
	release								NULL,
	setup								CHOICE {
		scheduled-r13					SEQUENCE {
			discTxConfig-r13					SL-DiscResourcePool-r12	OPTIONAL, -- Need ON
			discTF-IndexList-r13				SL-TF-IndexPairList-r12b	OPTIONAL, -- Need ON
			discHoppingConfig-r13				SL-HoppingConfigDisc-r12
													OPTIONAL	-- Need ON
		},
		ue-Selected-r13					SEQUENCE {
			discTxPoolDedicated-r13			SEQUENCE {
				poolToReleaseList-r13			SL-TxPoolToReleaseList-r12 OPTIONAL,	-- Need ON
				poolToAddModList-r13			SL-DiscTxPoolToAddModList-r12 OPTIONAL	-- Need ON
			} 													OPTIONAL	-- Need ON
		}
	}
}

SL-DiscTxPoolToAddModList-r12 ::=		SEQUENCE (SIZE (1..maxSL-TxPool-r12)) OF SL-DiscTxPoolToAddMod-r12

SL-DiscTxPoolToAddMod-r12 ::=		SEQUENCE	{
	poolIdentity-r12					SL-TxPoolIdentity-r12,
	pool-r12							SL-DiscResourcePool-r12
}

SL-DiscTxConfigScheduled-r13 ::=			SEQUENCE {
	discTxConfig-r12					SL-DiscResourcePool-r12	OPTIONAL, -- Need ON
	discTF-IndexList-r12				SL-TF-IndexPairList-r12 	OPTIONAL, -- Need ON
	discHoppingConfig-r12				SL-HoppingConfigDisc-r12
}

SL-DiscTxPoolDedicated-r13 ::=			SEQUENCE {
	poolToReleaseList-r12			SL-TxPoolToReleaseList-r12 OPTIONAL,	-- Need ON
	poolToAddModList-r12			SL-DiscTxPoolToAddModList-r12 OPTIONAL	-- Need ON
}

SL-TF-IndexPairList-r12 ::=		SEQUENCE (SIZE (1..maxSL-TF-IndexPair-r12)) OF SL-TF-IndexPair-r12

SL-TF-IndexPair-r12 ::=		SEQUENCE	{
	discSF-Index-r12					INTEGER (1.. 200)		OPTIONAL,	-- Need ON
	discPRB-Index-r12					INTEGER (1.. 50)		OPTIONAL	-- Need ON
}

SL-TF-IndexPairList-r12b ::=		SEQUENCE (SIZE (1..maxSL-TF-IndexPair-r12)) OF SL-TF-IndexPair-r12b

SL-TF-IndexPair-r12b ::=		SEQUENCE	{
	discSF-Index-r12b					INTEGER (0..209)		OPTIONAL,	 -- Need ON
	discPRB-Index-r12b					INTEGER (0..49)			OPTIONAL	 -- Need ON
}

SL-DiscTxRefCarrierDedicated-r13 ::=	CHOICE {
	pCell								NULL,
	sCell								SCellIndex-r10
}

-- ASN1STOP

SL-DiscConfig field descriptions
discTxRefCarrierDedicated
Indicates if the PCell or an SCell is to be used as reference DL measurements and synchronization, instead of the frequency used to transmit sidelink discovery announcements on, see TS 36.213 [23, 14.3.1].
discTxInterFreqInfo
Indicates frequency applicable for the resources indicated by discTxResources, and possibly resource allocations on additional frequencies by field discTxInfoInterFreqListExt.
discTF-IndexList
Indicates a list of time-frequency resource indices pair where each pair of indices corresponds to one discovery message. E-UTRAN only configures discTF-IndexList-r12b when configuring the UE with scheduled SL discovery Tx resources. When receiving discTF-IndexList-r12b, the UE shall only consider this field (and hence ignore discTF-IndexList-r12, if included or previously configured).
discTxResources
Indicates the resources assigned to the UE for discovery announcements, which can either be a pool from which the UE may select or a set of resources specifically assigned for use by the UE.
discTxConfig
Indicates the resources configuration used when E-UTRAN schedules Tx resources (i.e. the fields discSF-Index and discPRB-Index indicate the actual resources to be used).
SL-TF-IndexPair
A pair of indices, one for the time domain and one for the frequency domain, indicating the start of resources within the pool covered by discTxConfig, see TS 36.211 [21, 9.5.6] for one discovery message. The upper limits of discSF-Index and discPRB-Index are defined in TS 36.213 [23, 14.3.1].
discSysInfoReportConfig
Indicates the request to start a SidelinkUEInformation procedure for reporting system information acquired during an inter-frequency discovery procedure. When receving a discSysInfoReportConfig setup, the UE shall start timer T370 with the timer value set to [60] seconds. When receiving a discSysInfoReportConfig release, the UE shall stop timer T370.

Conditional presence
Explanation
DiscTxSetup
The field is mandatory present if discTxResources are being established (either normal or for relay discovery); otherwise it is not present.

-	SL-DiscResourcePool
The IE SL-DiscResourcePool specifies the configuration information for an individual pool of resources for sidelink discovery.
SL-DiscResourcePool information element
-- ASN1START

SL-DiscTxPoolList-r12 ::=		SEQUENCE (SIZE (1..maxSL-TxPool-r12)) OF SL-DiscResourcePool-r12

SL-DiscRxPoolList-r12 ::=		SEQUENCE (SIZE (1..maxSL-RxPool-r12)) OF SL-DiscResourcePool-r12

SL-DiscResourcePool-r12 ::=		SEQUENCE	{
	cp-Len-r12						SL-CP-Len-r12,
	discPeriod-r12				ENUMERATED {rf32, rf64, rf128,
											rf256, rf512, rf1024, rf16-v13x0, spare},
	numRetx-r12					INTEGER (0..3),
	numRepetition-r12				INTEGER (1..50),
	tf-ResourceConfig-r12			SL-TF-ResourceConfig-r12,
	txParameters-r12				SEQUENCE {
		txParametersGeneral-r12		SL-TxParameters-r12,
		ue-SelectedResourceConfig-r12	SEQUENCE {
			poolSelection-r12				CHOICE {
				rsrpBased-r12					SL-PoolSelectionConfig-r12,
				random-r12						NULL
			},
			txProbability-r12			ENUMERATED {p25, p50, p75, p100}
		}															OPTIONAL 	-- Need OR
	}																OPTIONAL, 	-- Cond Tx
	rxParameters-r12				SEQUENCE {
		tdd-Config-r12					TDD-Config					OPTIONAL, 	-- Need OR
		syncConfigIndex-r12			INTEGER (0..15)
	}																OPTIONAL, 	-- Need OR
	...,
	[[	discPeriod-v13x0				CHOICE {
			release								NULL,
			setup								ENUMERATED {rf4, rf7, rf8, rf14, rf28,
													spare3, spare2, spare}
			}														OPTIONAL,	-- Need ON
	-- Note: Extended values apply for PS discovery (not only for relay). E-UTRAN sets original
	-- field to spare value to ensure legacy UEs ignore the concerned entry
		rxParamsAddNeighFreq-r13		SEQUENCE {
			physCellId-r13					PhysCellId
		}															OPTIONAL,	-- Need ON
		txParamsAddNeighFreq-r13		SEQUENCE {
			physCellId-r13					PhysCellId,
			p-Max							P-Max					OPTIONAL,	-- Need OP
			tdd-Config-r13					TDD-Config				OPTIONAL,	-- Need OR
			tdd-Config-v1130				TDD-Config-v1130		OPTIONAL,	-- Cond TDD-OR
			freqInfo							SEQUENCE {
				ul-CarrierFreq						ARFCN-ValueEUTRA	OPTIONAL,	-- Need OP
				ul-Bandwidth						ENUMERATED {n6, n15, n25, n50, n75, n100}
																			OPTIONAL,	-- Need OP
			additionalSpectrumEmission			AdditionalSpectrumEmission
			},
			referenceSignalPower				INTEGER (-60..50),
			syncConfigIndex-r13				INTEGER (0..15)			OPTIONAL	-- Need OR
		}															OPTIONAL	-- Need ON
	]]
}

SL-PoolSelectionConfig-r12 ::=		SEQUENCE {
	threshLow-r12							RSRP-RangeSL2-r12,
	threshHigh-r12							RSRP-RangeSL2-r12
}

-- ASN1STOP

SL-DiscResourcePool field descriptions
discPeriod
Indicates the period over which resources are allocated in a cell for discovery message transmission/reception, see PSDCH period in TS 36.213 [23]. Value in number of radio frames. Value rf32 corresponds to 32 radio frames, rf64 corresponds to 64 radio frames and so on.
numRepetition
Indicates the number of times subframeBitmap is repeated for mapping to subframes that occurs within a discPeriod. The highest value E-UTRAN uses is value 5 for FDD and TDD configuration 0, value 13 for TDD configuration 1, value 25 for TDD configuration 2, value 17 for TDD configuration 3, value 25 for TDD configuration 4, value 50 for TDD configuration 5 and value 7 for TDD configuration 6. E-UTRAN configures numRepetition and subframeBitmap such that the mapped subframes do not exceed the discPeriod.
poolSelection
Indicates the mechanism for selecting a (transmission) pool when multiple candidates are provided. E-UTRAN configures the same value (i.e. a pool selection method) for all candidate pools within one pool list (discTxPoolCommon or discTxPoolDedicated) but the pool selection method in different pool lists may or may not be the same.
syncConfigIndex
Indicates the synchronisation configuration that is associated with a reception pool, by means of an index to the corresponding entry of discSyncConfig in SystemInformationBlockType19.
threshLow, threshHigh
Specifies the thresholds used to select a resource pool in RSRP based pool selection. The E-UTRAN should configure threshLow and threshHigh such that the UE selects only one resource pool upon RSRP based pool selection. 
txProbability
Indicates the probability of transmitting announcement in a discovery period when configured with a pool of resources, see TS 36.321 [6].

Conditional presence
Explanation
TDD-OR
The field is optional present for TDD, need OR; it is not present for FDD.
Tx
The field is mandatory present when included in discTxPoolDedicated or discTxPoolCommon. Otherwise the field is not present.

-	SL-DiscTxPowerInfo
The IE SL-DiscTxPowerInfo specifies power control parameters for one or more power classes.
SL-DiscTxPowerInfo information element
-- ASN1START

SL-DiscTxPowerInfoList-r12 ::= 	SEQUENCE (SIZE (maxSL-DiscPowerClass-r12)) OF SL-DiscTxPowerInfo-r12

SL-DiscTxPowerInfo-r12 ::= 				SEQUENCE	{
	discMaxTxPower-r12							P-Max,
	...
}

-- ASN1STOP

SL-DiscTxPowerInfo field descriptions
discMaxTxPower
Indicates the P-Max parameter used to calculate the maximum transmit power a UE configured with the concerned range class, see TS 24.333 [70, 4.2.11]. The first entry in SL-DiscTxPowerInfoList corresponds to UE range class 'short', the second entry corresponds to 'medium' and the third entry corresponds to 'long'.

-	SL-GapConfig
The IE SL-GapConfig indicates the gaps assigned by E-UTRAN to enable the UE to receive or transmit sidelink discovery, intra or inter frequency.
SL-GapConfig information element
-- ASN1START

SL-GapConfig-r13 ::=				SEQUENCE {
	gapPatternList-r13				SL-GapPatternList-r13
}

SL-GapPatternList-r13 ::=	SEQUENCE (SIZE (1..maxSL-GP-r13)) OF SL-GapPattern-r13

SL-GapPattern-r13 ::=				SEQUENCE {
	gapPeriod-r13						ENUMERATED {rf4, rf7, rf8, rf14, rf16, rf28, rf32,
											 rf64, rf128, rf256, rf512, rf1024, spare},
	gapOffset-r12						SL-OffsetIndicator-r12,
	gapSubframeBitmap-r13 				BIT STRING (SIZE (1..10240))
}

-- ASN1STOP

SL-GapConfig field descriptions
gapSubframeBitmap
Indicates the subframes of one or more individual gaps, not only covering the subframes of the associated discovery resources but also including e.g. re-tuning delays. The UE and E-UTRAN signal bit strings of valid sizes only i.e. sizes up to (10* gapPeriod).

-	SL-GapRequest
The IE SL-GapRequest indicates the gaps requested by the UE to receive or transmit sidelink discovery, intra or inter frequency.
SL-GapRequest information element
-- ASN1START

SL-GapRequest-r13 ::=				SEQUENCE (SIZE (1..maxFreq)) OF SL-GapFreqInfo-r13

SL-GapFreqInfo-r13 ::=				SEQUENCE {
	carrierFreq-r13					ARFCN-ValueEUTRA-r9					OPTIONAL,
	gapPatternList-r13				SL-GapPatternList-r13
}

-- ASN1STOP

-	SL-HoppingConfig
The IE SL-HoppingConfig indicates the hopping configuration used for sidelink.
SL-HoppingConfig information element
-- ASN1START

SL-HoppingConfigComm-r12 ::=		SEQUENCE	{
	hoppingParameter-r12				INTEGER (0..504),
	numSubbands-r12						ENUMERATED {ns1, ns2, ns4},
	rb-Offset-r12						INTEGER (0..110)
}

SL-HoppingConfigDisc-r12 ::=	SEQUENCE	{
	a-r12									INTEGER (1..200),
	b-r12									INTEGER (1..10),
	c-r12									ENUMERATED {n1, n5}
}

-- ASN1STOP

SL-HoppingConfig field descriptions
a
Per cell parameter:  see TS 36.213 [23, 14.3.1].
b
Per UE parameter:  see TS 36.213 [23, 14.3.1]. 
c
Per cell parameter:  see TS36.213 [23, 14.3.1]
hoppingParameter
Affects the hopping performed as specificed in TS 36.213 [23, 14.1.1.2 and 14.1.1.4]. In case value 504 is received, the value used by the UE is 510.
numSubbands
Parameter: Nsb see TS 36.211 [21, 9.3.6].
rb-Offset
Parameter: , see TS 36.211 [21, 9.3.6].

-	SL-OffsetIndicator
The IE SL-OffsetIndicator indicates the offset of the pool of resources relative to SFN 0 of the cell from which it was obtained or, when out of coverage, relative to DFN 0.
SL-OffsetIndicator information element
-- ASN1START

SL-OffsetIndicator-r12 ::=			CHOICE {
	small-r12								INTEGER (0..319),
	large-r12								INTEGER (0..10239)
}

SL-OffsetIndicatorSync-r12 ::=			INTEGER (0..39)

-- ASN1STOP

SL-OffsetIndicator field descriptions
SL-OffsetIndicator
In sc-TF-ResourceConfig, it indicates the offset of the first period of pool of resources within a SFN cycle. For data-TF-ResourceConfig, it corresponds to the offsetIndicator as defined in TS 36.213 [23, 14.1.3].
SL-OffsetIndicatorSync
Synchronisation resources are present in those SFN and subframes which satisfy the relation: (SFN*10+ Subframe Number) mod 40 = SL-OffsetIndicatorSync.

-	SL-PeriodComm
The IE SL-PeriodComm indicates the period over which resources allocated in a cell for sidelink communication.
SL-PeriodComm information element
-- ASN1START

SL-PeriodComm-r12 ::=					ENUMERATED {sf40, sf60, sf70, sf80, sf120, sf140,
												 sf160, sf240, sf280, sf320, spare6, spare5,
												 spare4, spare3, spare2, spare}

-- ASN1STOP

-	SL-Priority
The IE SL-Priority indicates the priority of resource pool used for sidelink communication, see TS 36.211 [21].
SL-Priority information element
-- ASN1START

SL-PriorityList-r13 ::=		SEQUENCE (SIZE (1..maxSL-Prio-r13)) OF SL-Priority-r13

SL-Priority-r13 ::=			INTEGER (1..8)

-- ASN1STOP

-	SLSSID
The IE SLSSID identifies a cell and is used by the receiving UE to detect asynchronous neighbouring cells, and by transmitting UEs to extend the synchronisation signals beyond the cell's coverage area.
SLSSID information element
-- ASN1START

SLSSID-r12 ::=					INTEGER (0..167)

-- ASN1STOP

-	SL-SyncConfig
The IE SL-SyncConfig specifies the configuration information concerning reception of synchronisation signals from neighbouring cells as well as concerning the transmission of synchronisation signals for sidelink communication and sidelink discovery.
SL-SyncConfig information element
-- ASN1START

SL-SyncConfigList-r12 ::=		SEQUENCE (SIZE (1..maxSL-SyncConfig-r12)) OF SL-SyncConfig-r12

SL-SyncConfig-r12 ::=					SEQUENCE {
	syncCP-Len-r12							SL-CP-Len-r12,
	syncOffsetIndicator-r12				SL-OffsetIndicatorSync-r12,
	slssid-r12								SLSSID-r12,
	txParameters-r12							SEQUENCE {
		syncTxParameters-r12					SL-TxParameters-r12,
		syncTxThreshIC-r12						RSRP-RangeSL-r12,
		syncInfoReserved-r12						BIT STRING (SIZE (19))	OPTIONAL 	-- Need OR
	}																	OPTIONAL, 	-- Need OR
	rxParamsNCell-r12						SEQUENCE {
		physCellId-r12							PhysCellId,
		discSyncWindow-r12				ENUMERATED {w1, w2}
	}																	OPTIONAL, 	-- Need OR
	...,
	[[	syncTxPeriodic-r13					ENUMERATED {true}			OPTIONAL	-- Need OR
	]]
}

SL-SyncConfigListNFreq-r12 ::=		SEQUENCE (SIZE (1..maxSL-SyncConfig-r12)) OF SL-SyncConfigNFreq-r13

SL-SyncConfigNFreq-r13 ::=			SEQUENCE {
	asyncParameters-r13					SEQUENCE {
		syncCP-Len-r13						SL-CP-Len-r12,
		syncOffsetIndicator-r13				SL-OffsetIndicatorSync-r12,
		slssid-r13							SLSSID-r12
	}																OPTIONAL,	-- Need OR
	txParameters-r13					SEQUENCE {
		syncTxParameters-r13				SL-TxParameters-r12,
		syncTxThreshIC-r13					RSRP-RangeSL-r12,
		syncInfoReserved-r13					BIT STRING (SIZE (19))	OPTIONAL,	-- Need OR
		syncTxPeriodic-r13					ENUMERATED {true}		OPTIONAL	-- Need OR
	}																OPTIONAL,	-- Need OR
	rxParameters-r1s					SEQUENCE {
		discSyncWindow-r13					ENUMERATED {w1, w2}
	}																	OPTIONAL, 	-- Need OR
	...
}
-- ASN1STOP

SL-SyncConfig field descriptions
discSyncWindow
Indicates the synchronization window over which the UE expects that SLSS or discovery resources indicated by the pool configuration (see TS 36.213 [23, 14.4]). The value w1 denotes 5 milliseconds. The value w2 denotes the length corresponding to normal cyclic prefix divided by 2.
syncInfoReserved
Reserved for future use.
syncOffsetIndicator
E-UTRAN should ensure syncOffsetIndicator is set to the same value as syncOffsetIndicator1 or syncOffsetIndicator2 in preconfigSync within SL-Preconfiguration, if configured.
syncTxPeriodic
Indicates whether in each discovery period in which UE transmits discovery, the UE transmits SLSS once or perodically (i.e. every 40ms). In the latter case (periodic) the UE also transmits the MasterInformationBlock-SL message alongside. E-UTRAN configures this field only for synchronisation configurations applicable for PS discovery.
syncTxThreshIC
Indicates the threshold used while in coverage. In case the RSRP measurement of the cell chosen for transmission of sidelink communication/ discovery announcements, is below the level indicated by this field, the UE may transmit SLSS (i.e. become synchronisation reference) when performing the corresponding sidelink transmission..
txParameters
Includes parameters relevant only for transmission. E-UTRAN includes the field in one entry per list, as included in commSyncConfig or discSyncConfig.

-	SL-SysInfoReport
The IE SL-SysInfoReport contains the parameters related to Sidelink operations from system information of inter-frequency cells
SL-SysInfoReport information element
-- ASN1START

SL-SysInfoReport-r13 ::=			SEQUENCE {
	plmn-IdentityList-r13				PLMN-IdentityList			OPTIONAL,
	cellIdentity-13						CellIdentity				OPTIONAL,
	carrierFreqInfo-13					ARFCN-ValueEUTRA-r9			OPTIONAL,
	discRxResources-r13					SL-DiscRxPoolList-r12		OPTIONAL,
	discTxPoolCommon-r13				SL-DiscTxPoolList-r12 		OPTIONAL,
	discTxPowerInfo-r13					SL-DiscTxPowerInfoList-r12	OPTIONAL,
	discSyncConfig-r13				SEQUENCE {
		asyncParameters-r13					SEQUENCE {
			syncCP-Len-r13						SL-CP-Len-r12,
			syncOffsetIndicator-r13				SL-OffsetIndicatorSync-r12,
			slssid-r13							SLSSID-r12
		}															OPTIONAL,
		txParameters-r13					SEQUENCE {
			syncTxParameters-r13				SL-TxParameters-r12,
			syncTxThreshIC-r13					RSRP-RangeSL-r12,
			syncInfoReserved-r13				BIT STRING (SIZE (19))	OPTIONAL,
			syncTxPeriodic-r13					ENUMERATED {true}		OPTIONAL
		}																OPTIONAL
	}																OPTIONAL,
	cellSelectionInfo-r13			SEQUENCE {
		q-RxLevMin-r13					Q-RxLevMin,
		q-RxLevMinOffset-r13			INTEGER (1..8)				OPTIONAL
	}	OPTIONAL,
	q-Hyst-r13						ENUMERATED {
												dB0, dB1, dB2, dB3, dB4, dB5, dB6, dB8, dB10,
												dB12, dB14, dB16, dB18, dB20, dB22, dB24}
																	OPTIONAL,
	q-RxLevMin-r13					Q-RxLevMin	OPTIONAL,
	t-ReselectionEUTRA-r13			T-Reselection	OPTIONAL,
	tdd-Config-r13					TDD-Config		OPTIONAL,
	freqInfo-r13					SEQUENCE {
		ul-CarrierFreq-r13				ARFCN-ValueEUTRA				OPTIONAL,	
		ul-Bandwidth-r13				ENUMERATED {n6, n15, n25, n50, n75, n100}
																		OPTIONAL,	
		additionalSpectrumEmission-r13	AdditionalSpectrumEmission		OPTIONAL
	}																OPTIONAL,
	p-Max-r13						P-Max	OPTIONAL,
	referenceSignalPower-r13		INTEGER (-60..50)	OPTIONAL
}

-- ASN1STOP

SL-SysInfoReport field descriptions
plmn-IdentityList
Indicates the list of PLMN identity of the cell from which the UE acquired the system information relevant for discovery
cellIdentity
Indicated the identity of the cell from which the UE acquired the system information relevant for discovery
SL-CarrierFreqInfo
Indicates the frequency of the cell from which the UE acquired the system information relevant for discovery

-	SL-TF-ResourceConfig
The IE SL-TF-ResourceConfig specifies a set of time/ frequency resources used for sidelink.
SL-TF-ResourceConfig information element
-- ASN1START

SL-TF-ResourceConfig-r12 ::=		SEQUENCE	{
	prb-Num-r12							INTEGER (1..100),
	prb-Start-r12 				 		INTEGER (0..99),
	prb-End-r12				 			INTEGER (0..99),
	offsetIndicator-r12					SL-OffsetIndicator-r12,
	subframeBitmap-r12 					SubframeBitmapSL-r12
}

SubframeBitmapSL-r12 ::=		CHOICE {
	bs4-r12									BIT STRING (SIZE (4)),
	bs8-r12									BIT STRING (SIZE (8)),
	bs12-r12								BIT STRING (SIZE (12)),
	bs16-r12								BIT STRING (SIZE (16)),
	bs30-r12								BIT STRING (SIZE (30)),
	bs40-r12								BIT STRING (SIZE (40)),
	bs42-r12								BIT STRING (SIZE (42))
}

-- ASN1STOP

SL-TF-ResourceConfig field descriptions
prb-Start, prb-End, prb-Num
Sidelink transmissions on a sub-frame can occur on PRB with index greater than or equal to prb-Start and less than prb-Start + prb-Num, and on PRB with index greater than prb-End - prb-Num and less than or equal to prb-End. Even for neighbouring cells, prb-Start and prb-End , are relative to PRB #0 of the cell from which it was obtained. See TS36.213 [23, 14.1.3, 14.2.3, 14.3.3].
subframeBitmap
Indicates the subframe bitmap indicating resources used for sidelink. E-UTRAN configures value bs40 for FDD and the following values for TDD: value bs42 for configuration0, value bs16 for configuration1, value bs8 for configuration2, value bs12 for configuration3, value bs8 for configuration4, value bs4 for configuration5 and value bs30 for configuration6.

-	SL-TxParameters
The IE SL-TxParameters identifies a set of parameters configured for sidelink transmission, used for communication, discovery and synchronisation.
SL-TxParameters information element
-- ASN1START

SL-TxParameters-r12 ::=				SEQUENCE	{
	alpha-r12								Alpha-r12,
	p0-r12									P0-SL-r12
}

P0-SL-r12 ::=							INTEGER (-126..31)

-- ASN1STOP

SL-TxParameters field descriptions
alpha
Parameter(s): ,,,,, See TS 36.213 [23, 14.1.1.5, 14.2.1.2, 14.3.1, 14.4] where al0 corresponds to 0, al04 corresponds to value 0.4, al05 to 0.5, al06 to 0.6, al07 to 0.7, al08 to 0.8, al09 to 0.9 and al1 corresponds to 1. This field applies for sidelink power control.
p0
Parameter: ,,,,, see TS 36.213 [23, 14.1.1.5, 14.2.1.2, 14.3.1, 14.4], unit dBm.

-	SL-TxPoolIdentity
The IE SL-TxPoolIdentity identifies an individual pool entry configured for sidelink transmission, used for communication and discovery.
SL-TxPoolIdentity information element
-- ASN1START

SL-TxPoolIdentity-r12 ::=			INTEGER (1.. maxSL-TxPool-r12)

SL-CommTxPoolIdentity-v13x0 ::=		INTEGER (maxSL-CommTxPool-r12Plus1-r13.. maxSL-CommTxPool-r13)

SL-CommTxPoolIdentity-r13 ::=		INTEGER (1.. maxSL-CommTxPool-r13)

-- ASN1STOP

-	SL-TxPoolToReleaseList
The IE SL-TxPoolToReleaseList is used to release one or more individual pool entries used for sidelink transmission, for communication and discovery.
SL-TxPoolToReleaseList information element
-- ASN1START

SL-TxPoolToReleaseList-r12 ::=	SEQUENCE (SIZE (1..maxSL-TxPool-r12)) OF SL-TxPoolIdentity-r12

SL-TxPoolToReleaseListExt-r13 ::=	SEQUENCE (SIZE (1..maxSL-CommTxPool-v13x0)) OF SL-CommTxPoolIdentity-v13x0

-- ASN1STOP

6.4	RRC multiplicity and type constraint values
-	Multiplicity and type constraint definitions
-- ASN1START
maxACDC-Cat-r13				INTEGER ::=	16	-- Maximum number of ACDC categories (per PLMN)
maxBandComb-r10				INTEGER ::=	128	-- Maximum number of band combinations.
maxBandComb-r11				INTEGER ::=	256	-- Maximum number of additional band combinations.
maxBandComb-r13				INTEGER ::=	384 -- Maximum number of band combinations in Rel-13
maxBands					INTEGER ::= 64	-- Maximum number of bands listed in EUTRA UE caps
maxBandwidthClass-r10		INTEGER ::=	16	-- Maximum number of supported CA BW classes per band
maxBandwidthCombSet-r10		INTEGER ::=	32	-- Maximum number of bandwidth combination sets per
											-- supported band combination
maxCDMA-BandClass			INTEGER ::= 32	-- Maximum value of the CDMA band classes
maxCellBlack				INTEGER ::= 16	-- Maximum number of blacklisted physical cell identity
											-- ranges listed in SIB type 4 and 5
maxCellHistory-r12			INTEGER ::= 16	-- Maximum number of visited EUTRA cells reported
maxCellInfoGERAN-r9 		INTEGER ::=	32	-- Maximum number of GERAN cells for which system in-
											-- formation can be provided as redirection assistance
maxCellInfoUTRA-r9			INTEGER ::=	16	-- Maximum number of UTRA cells for which system
											-- information can be provided as redirection
											-- assistance
maxCombIDC-r11				INTEGER ::= 128	-- Maximum number of reported UL CA combinations
maxCSI-IM-r11				INTEGER ::= 3	-- Maximum number of CSI-IM configurations
											-- (per carrier frequency)
maxCSI-IM-r12				INTEGER ::= 4	-- Maximum number of CSI-IM configurations
											-- (per carrier frequency)
maxCSI-Proc-r11				INTEGER ::= 4	-- Maximum number of CSI processes (per carrier
											--  frequency)
maxCSI-RS-NZP-r11			INTEGER ::= 3	-- Maximum number of CSI RS resource
											--  configurations using non-zero Tx power
											--  (per carrier frequency)
maxCSI-RS-ZP-r11			INTEGER ::= 4	-- Maximum number of CSI RS resource
											--  configurations using zero Tx power(per carrier
											--  frequency)
maxCQI-ProcExt-r11			INTEGER ::= 3	-- Maximum number of additional periodic CQI
											-- configurations (per carrier frequency)
maxFreqUTRA-TDD-r10			INTEGER ::=	6	-- Maximum number of UTRA TDD carrier frequencies for
											-- which system information can be provided as
											-- redirection assistance
maxCellInter				INTEGER ::= 16	-- Maximum number of neighbouring inter-frequency
											-- cells listed in SIB type 5
maxCellIntra				INTEGER ::= 16	-- Maximum number of neighbouring intra-frequency
											-- cells listed in SIB type 4
maxCellListGERAN			INTEGER ::= 3	-- Maximum number of lists of GERAN cells
maxCellMeas					INTEGER ::= 32	-- Maximum number of entries in each of the
											-- cell lists in a measurement object
maxCellReport				INTEGER ::= 8	-- Maximum number of reported cells/CSI-RS resources
maxCSI-RS-Meas-r12			INTEGER ::= 96	-- Maximum number of entries in the CSI-RS list
											-- in a measurement object
maxDRB						INTEGER ::= 11	-- Maximum number of Data Radio Bearers
maxDS-Duration-r12			INTEGER ::= 5	-- Maximum number of subframes in a discovery signals
											-- occasion
maxDS-ZTP-CSI-RS-r12		INTEGER ::= 5	-- Maximum number of zero transmission power CSI-RS for
											-- a serving cell concerning discovery signals
maxEARFCN					INTEGER ::= 65535	-- Maximum value of EUTRA carrier frequency
maxEARFCN-Plus1				INTEGER ::= 65536	-- Lowest value extended EARFCN range
maxEARFCN2					INTEGER ::= 262143	-- Highest value extended EARFCN range
maxEPDCCH-Set-r11			INTEGER ::= 2	-- Maximum number of EPDCCH sets
maxFBI						INTEGER ::= 64	-- Maximum value of fequency band indicator
maxFBI-Plus1					INTEGER ::= 65	-- Lowest value extended FBI range
maxFBI2						INTEGER ::= 256	-- Highest value extended FBI range
maxFreq						INTEGER ::= 8	-- Maximum number of carrier frequencies
maxFreqIDC-r11				INTEGER ::= 32	-- Maximum number of carrier frequencies that are
											-- affected by the IDC problems
maxFreqMBMS-r11				INTEGER ::= 5	-- Maximum number of carrier frequencies for which an 
											-- MBMS capable UE may indicate an interest
maxGERAN-SI					INTEGER ::= 10	-- Maximum number of GERAN SI blocks that can be
											-- provided as part of NACC information
maxGNFG						INTEGER ::= 16	-- Maximum number of GERAN neighbour freq groups
maxLCG-r13					INTEGER ::= 4	-- Maximum number of logical channel groups
maxLogMeasReport-r10		INTEGER ::= 520	-- Maximum number of logged measurement entries
											--  that can be reported by the UE in one message
maxMBSFN-Allocations		INTEGER ::= 8	-- Maximum number of MBSFN frame allocations with
											-- different offset
maxMBSFN-Area				INTEGER ::= 8
maxMBSFN-Area-1				INTEGER ::= 7
maxMBMSServiceListPerUE-r13		INTEGER ::= 16	-- Maximum number of services which the UE can
										-- include in the MBMS interest indication
maxMeasId					INTEGER ::= 32
maxMeasId-Plus1 			INTEGER ::= 33
maxMeasId-r12				INTEGER ::= 64
maxMultiBands				INTEGER ::= 8	-- Maximum number of additional frequency bands
											-- that a cell belongs to
maxNS-Pmax-r10				INTEGER ::= 8	-- Maximum number of NS and P-Max values per band
maxNAICS-Entries-r12			INTEGER ::= 8	-- Maximum number of supported NAICS combination(s)
maxNeighCell-r12				INTEGER ::= 8	-- Maximum number of neighbouring cells in NAICS
											-- configuration (per carrier frequency)
maxNeighCellSCPTM-r13		INTEGER ::=	8	-- Maximum number of SCPTM neighbour cells
maxObjectId					INTEGER ::= 32
maxP-a-PerNeighCell-r12		INTEGER ::= 3	-- Maximum number of power offsets for a neighbour cell
											-- in NAICS configuration
maxPageRec					INTEGER ::= 16	-- 
maxPhysCellIdRange-r9 		INTEGER ::= 4	-- Maximum number of physical cell identity ranges
maxPLMN-r11					INTEGER ::=	6	-- Maximum number of PLMNs
maxPNOffset					INTEGER ::=	511	-- Maximum number of CDMA2000 PNOffsets
maxPMCH-PerMBSFN			INTEGER ::= 15
maxQCI-r13					INTEGER ::= 6   -- Maximum number of QCIs
maxRAT-Capabilities			INTEGER ::= 8	-- Maximum number of interworking RATs (incl EUTRA)
maxRE-MapQCL-r11			INTEGER ::= 4	-- Maximum number of PDSCH RE Mapping configurations
											--  (per carrier frequency)
maxReportConfigId			INTEGER ::= 32
maxRSTD-Freq-r10			INTEGER ::= 3	-- Maximum number of frequency layers for RSTD
											-- measurement
maxSAI-MBMS-r11				INTEGER ::= 64	-- Maximum number of MBMS service area identities
											-- broadcast per carrier frequency
maxSCell-r10				INTEGER ::= 4	-- Maximum number of SCells
maxSCell-r13				INTEGER ::= 31	-- Highest value of extended number range of SCells
maxSCell-Plus1				INTEGER ::= 5	-- Lowest value of extended number range of SCells
maxSC-MTCH-r13				INTEGER ::= 1024	-- Maximum number of SC-MTCHs in one cell
maxSL-CommRxPoolNFreq-r13	INTEGER ::= 32	-- Maximum number of individual sidelink communication
											-- Rx resource pools on neighbouring freq
maxSL-CommRxPoolPreconf-v13x0	INTEGER ::= 12	-- Maximum number of additional preconfigured
												-- sidelink communication Rx resource pool entries
maxSL-CommTxPool-r12Plus1-r13	INTEGER ::= 5	-- First additional individual sidelink
											-- communication Tx resource pool
maxSL-CommTxPool-v13x0			INTEGER ::= 4	-- Maximum number of additional sidelink
												-- communication Tx resource pool entries
maxSL-CommTxPool-r13			INTEGER ::= 8	-- Maximum number of individual sidelink
												-- communication Tx resource pools
maxSL-CommTxPoolPreconf-v13x0	INTEGER ::= 7	-- Maximum number of additional preconfigured
												-- sidelink communication Tx resource pool entries
maxSL-Dest-r12			INTEGER ::= 16	-- Maximum number of sidelink destinations
maxSL-DiscPowerClass-r12	INTEGER ::= 3	-- Maximum number of sidelink power classes
maxSL-DiscRxPoolPreconf-r13		INTEGER ::= 4	-- Maximum number of preconfigured sidelink
												-- discovery Rx resource pool entries
maxSL-DiscSysInfoReportFreq-r13	INTEGER ::= 8	-- Maximum number of frequencies to include in a
												-- UESidelinkInformation for SI reporting
maxSL-DiscTxPoolPreconf-r13		INTEGER ::= 1	-- Maximum number of preconfigured sidelink
												-- discovery Tx resource pool entries
maxSL-GP-r13			INTEGER ::= 8	-- Maximum number of gap patterns that can be requested
										-- for a frequency or assigned
maxSL-Prio-r13			INTEGER ::= 8	-- Maximum number of entries in sidelink priority list
maxSL-RxPool-r12			INTEGER ::= 16	-- Maximum number of individual sidelink Rx resource pools
maxSL-SyncConfig-r12		INTEGER ::= 16	-- Maximum number of sidelink Sync configurations
maxSL-TF-IndexPair-r12	INTEGER ::= 64	-- Maximum number of sidelink Time Freq resource index
											--  pairs
maxSL-TxPool-r12			INTEGER ::= 4	-- Maximum number of individual sidelink Tx resource pools
maxSTAG-r11					INTEGER ::= 3	-- Maximum number of STAGs
maxServCell-r10				INTEGER ::= 5	-- Maximum number of Serving cells
maxServCell-r13				INTEGER ::= 32	-- Highest value of extended number range of Serving cells
maxServCell-Plus1			INTEGER ::= 6	-- Lowest value of extended number range of Serving cells
maxServiceCount 			INTEGER ::= 16	-- Maximum number of MBMS services that can be included
											--  in an MBMS counting request and response
maxServiceCount-1			INTEGER ::= 15
maxSessionPerPMCH			INTEGER ::= 29
maxSessionPerPMCH-1			INTEGER ::= 28
maxSIB						INTEGER ::= 32	-- Maximum number of SIBs
maxSIB-1					INTEGER ::= 31
maxSI-Message				INTEGER ::= 32	-- Maximum number of SI messages
maxSimultaneousBands-r10	INTEGER ::= 64	-- Maximum number of simultaneously aggregated bands
maxSubframePatternIDC-r11	INTEGER ::= 8	-- Maximum number of subframe reservation patterns
											-- that the UE can simultaneously recommend to the
											-- E-UTRAN for use.
maxUTRA-FDD-Carrier			INTEGER ::= 16	-- Maximum number of UTRA FDD carrier frequencies
maxUTRA-TDD-Carrier			INTEGER ::= 16	-- Maximum number of UTRA TDD carrier frequencies
maxWLAN-Id-r12				INTEGER ::=	16	-- Maximum number of WLAN identifiers

-- ASN1STOP
NOTE: The value of maxDRB aligns with SA2.
-	End of EUTRA-RRC-Definitions
-- ASN1START

END
