-- 
-- ASN.1 module found by ./crfc2asn1.pl in EUTRA-RRC36331.txt at line 19467
-- 

EUTRA-InterNodeDefinitions DEFINITIONS AUTOMATIC TAGS ::=

BEGIN

IMPORTS
	AntennaInfoCommon,
	AntennaInfoDedicated-v10i0,
	ARFCN-ValueEUTRA,
	ARFCN-ValueEUTRA-v9e0,
	ARFCN-ValueEUTRA-r9,
	CellIdentity,
	C-RNTI,
	DL-DCCH-Message,
	DRB-Identity,
	DRB-ToReleaseList,
	FreqBandIndicator-r11,
	InDeviceCoexIndication-r11,
	MasterInformationBlock,
	maxBands,
	maxFreq,
	maxDRB,
	maxSCell-r10,
	maxSCell-r13,
	maxSCell-Plus1,
	maxServCell-r10,
	maxServCell-Plus1,
	maxServCell-r13,
	MBMSInterestIndication-r11,
	MeasConfig,
	MeasGapConfig,
	OtherConfig-r9,
	PhysCellId,
	P-Max,
	PowerCoordinationInfo-r12,
	SidelinkUEInformation-r12,
	SL-CommConfig-r12,
	SL-DiscConfig-r12,
	RadioResourceConfigDedicated,
	RSRP-Range,
	RSRQ-Range,
	RSRQ-Range-v1250,
	RS-SINR-Range-r13,
	SCellToAddModList-r10,
	SCellToAddModListExt-r13,
	SCG-ConfigPartSCG-r12,
	SecurityAlgorithmConfig,
	SCellIndex-r10,
	SCellIndex-r13,
	SCellToReleaseList-r10,
	SCellToReleaseListExt-r13,
	ServCellIndex-r10,
	ServCellIndexFull-r13,
	ShortMAC-I,
	MeasResultSSTD-r13,
	SystemInformationBlockType1,
	SystemInformationBlockType1-v890-IEs,
	SystemInformationBlockType2,
	UEAssistanceInformation-r11,
	UECapabilityInformation,
	UE-CapabilityRAT-ContainerList,
	UE-RadioPagingInfo-r12,
	WLAN-OffloadConfig-r12
FROM EUTRA-RRC-Definitions;

-- ASN1STOP

10.2.2	Message definitions
-	HandoverCommand
This message is used to transfer the handover command generated by the target eNB.
Direction: target eNB to source eNB/ source RAN
HandoverCommand message
-- ASN1START

HandoverCommand ::=					SEQUENCE {
	criticalExtensions					CHOICE {
		c1									CHOICE{
			handoverCommand-r8					HandoverCommand-r8-IEs,
			spare7 NULL,
			spare6 NULL, spare5 NULL, spare4 NULL,
			spare3 NULL, spare2 NULL, spare1 NULL
		},
		criticalExtensionsFuture			SEQUENCE {}
	}
}

HandoverCommand-r8-IEs ::=			SEQUENCE {
	handoverCommandMessage				OCTET STRING (CONTAINING DL-DCCH-Message),
	nonCriticalExtension				SEQUENCE {}							OPTIONAL
}

-- ASN1STOP

HandoverCommand field descriptions
handoverCommandMessage
Contains the entire DL-DCCH-Message including the RRCConnectionReconfiguration message used to perform handover within E-UTRAN or handover to E-UTRAN, generated (entirely) by the target eNB.

NOTE:	The source BSC, in case of inter-RAT handover from GERAN to E-UTRAN, expects that the HandoverCommand message includes DL-DCCH-Message only. Thus, criticalExtensionsFuture, spare1-spare7 and nonCriticalExtension should not be used regardless whether the source RAT is E-UTRAN, UTRAN or GERAN.
-	HandoverPreparationInformation
This message is used to transfer the E-UTRA RRC information used by the target eNB during handover preparation, including UE capability information.
Direction: source eNB/ source RAN to target eNB
HandoverPreparationInformation message
-- ASN1START

HandoverPreparationInformation ::=	SEQUENCE {
	criticalExtensions					CHOICE {
		c1									CHOICE{
			handoverPreparationInformation-r8	HandoverPreparationInformation-r8-IEs,
			spare7 NULL,
			spare6 NULL, spare5 NULL, spare4 NULL,
			spare3 NULL, spare2 NULL, spare1 NULL
		},
		criticalExtensionsFuture			SEQUENCE {}
	}
}

HandoverPreparationInformation-r8-IEs ::= SEQUENCE {
	ue-RadioAccessCapabilityInfo		UE-CapabilityRAT-ContainerList,
	as-Config							AS-Config					OPTIONAL, 		-- Cond HO
	rrm-Config							RRM-Config					OPTIONAL,
	as-Context							AS-Context				OPTIONAL, 		-- Cond HO
	nonCriticalExtension				HandoverPreparationInformation-v920-IEs		OPTIONAL
}

HandoverPreparationInformation-v920-IEs	::= SEQUENCE {
	ue-ConfigRelease-r9					ENUMERATED {
										rel9, rel10, rel11, rel12, v10j0, v11e0,
										v1280, spare1, ...} 			OPTIONAL, 	-- Cond HO2
	nonCriticalExtension				HandoverPreparationInformation-v9d0-IEs		OPTIONAL
}

HandoverPreparationInformation-v9d0-IEs	::= SEQUENCE {
	lateNonCriticalExtension			OCTET STRING (CONTAINING HandoverPreparationInformation-v9j0-IEs)	OPTIONAL,
	nonCriticalExtension				HandoverPreparationInformation-v9e0-IEs			OPTIONAL
}

-- Late non-critical extensions:
HandoverPreparationInformation-v9j0-IEs ::= SEQUENCE {
	-- Following field is only for pre REL-10 late non-critical extensions
	lateNonCriticalExtension			OCTET STRING					OPTIONAL,
	nonCriticalExtension				HandoverPreparationInformation-v10j0-IEs		OPTIONAL
}

HandoverPreparationInformation-v10j0-IEs ::= SEQUENCE {
	as-Config-v10j0						AS-Config-v10j0			OPTIONAL,
	-- Following field is only for late non-critical extensions from REL-10
	nonCriticalExtension				SEQUENCE {}				OPTIONAL
}

-- Regular non-critical extensions:
HandoverPreparationInformation-v9e0-IEs	::= SEQUENCE {
	as-Config-v9e0						AS-Config-v9e0					OPTIONAL,	-- Cond HO2
	nonCriticalExtension				HandoverPreparationInformation-v1130-IEs		OPTIONAL
}

HandoverPreparationInformation-v1130-IEs	::= SEQUENCE {
	as-Context-v1130					AS-Context-v1130				OPTIONAL,	-- Cond HO2
	nonCriticalExtension				HandoverPreparationInformation-v1250-IEs						OPTIONAL
}

HandoverPreparationInformation-v1250-IEs ::= SEQUENCE {
	ue-SupportedEARFCN-r12 				ARFCN-ValueEUTRA-r9				OPTIONAL,	-- Cond HO3
	as-Config-v1250					AS-Config-v1250				OPTIONAL, 	-- Cond HO2 
	nonCriticalExtension				SEQUENCE {}						OPTIONAL
}

-- ASN1STOP

HandoverPreparationInformation field descriptions
as-Config
The radio resource configuration. Applicable in case of intra-E-UTRA handover. If the target receives an incomplete MeasConfig and RadioResourceConfigDedicated in the as-Config, the target eNB may decide to apply the full configuration option based on the ue-ConfigRelease.
as-Context
Local E-UTRAN context required by the target eNB.
rrm-Config
Local E-UTRAN context used depending on the target node's implementation, which is mainly used for the RRM purpose.
ue-ConfigRelease
Indicates the RRC protocol release or version applicable for the current UE configuration. This could be used by target eNB to decide if the full configuration approach should be used. If this field is not present, the target assumes that the current UE configuration is based on the release 8 version of RRC protocol. NOTE 1.
ue-RadioAccessCapabilityInfo
NOTE 2
ue-SupportedEARFCN
Includes UE supported EARFCN of the handover target E-UTRA cell if the target E-UTRA cell belongs to multiple frequency bands.

NOTE 1:	The source typically sets the ue-ConfigRelease to the release corresponding with the current dedicated radio configuration. The source may however also consider the common radio resource configuration e.g. in case interoperability problems would appear if the UE temporary continues extensions of this part of the configuration in a target PCell not supporting them.
NOTE 2:	The following table indicates per source RAT whether RAT capabilities are included or not.
Source RAT
E-UTRA capabilites
UTRA capabilities
GERAN capabilities
UTRAN
Included
May be included, ignored by eNB if received
May be included
GERAN CS
Excluded
May be included, ignored by eNB if received
Included
GERAN PS
Excluded
May be included, ignored by eNB if received
Included
E-UTRAN
Included
May be included
May be included

Conditional presence
Explanation
HO
The field is mandatory present in case of handover within E-UTRA; otherwise the field is not present.
HO2
The field is optional present in case of handover within E-UTRA; otherwise the field is not present.
HO3
The field is optional present in case of handover from GERAN to E-UTRA, otherwise the field is not present.

-	SCG-Config
This message is used to transfer the SCG radio configuration generated by the SeNB.
Direction: Secondary eNB to master eNB
SCG-Config message
-- ASN1START

SCG-Config-r12 ::=					SEQUENCE {
	criticalExtensions					CHOICE {
		c1									CHOICE{
			scg-Config-r12					SCG-Config-r12-IEs,
			spare7 NULL,
			spare6 NULL, spare5 NULL, spare4 NULL,
			spare3 NULL, spare2 NULL, spare1 NULL
		},
		criticalExtensionsFuture			SEQUENCE {}
	}
}

SCG-Config-r12-IEs ::=				SEQUENCE {
	scg-RadioConfig-r12					SCG-ConfigPartSCG-r12				OPTIONAL,
	nonCriticalExtension				SEQUENCE {}							OPTIONAL
}

-- ASN1STOP

SCG-Config field descriptions
scg-RadioConfig-r12
Includes the change of the dedicated SCG configuration and, upon addition of an SCG cell, the common SCG configuration.
The SeNB only includes a new SCG cell in response to a request from MeNB, but may include release of an SCG cell release or release of the SCG part of an SCG/Split DRB without prior request from MeNB. The SeNB does not use this field to initiate release of the SCG.

-	SCG-ConfigInfo
This message is used by MeNB to request the SeNB to perform certain actions e.g. to establish, modify or release an SCG, and it may include additional information e.g. to assist the SeNB with assigning the SCG configuration.
Direction: Master eNB to secondary eNB
SCG-ConfigInfo message
-- ASN1START

SCG-ConfigInfo-r12 ::=					SEQUENCE {
	criticalExtensions					CHOICE {
		c1									CHOICE{
			scg-ConfigInfo-r12					SCG-ConfigInfo-r12-IEs,
			spare7 NULL,
			spare6 NULL, spare5 NULL, spare4 NULL,
			spare3 NULL, spare2 NULL, spare1 NULL
		},
		criticalExtensionsFuture			SEQUENCE {}
	}
}

SCG-ConfigInfo-r12-IEs ::=			SEQUENCE {
	radioResourceConfigDedMCG-r12	RadioResourceConfigDedicated		OPTIONAL,
	sCellToAddModListMCG-r12		SCellToAddModList-r10				OPTIONAL,
	measGapConfig-r12				MeasGapConfig						OPTIONAL,
	powerCoordinationInfo-r12		PowerCoordinationInfo-r12			OPTIONAL,
	scg-RadioConfig-r12				SCG-ConfigPartSCG-r12				OPTIONAL,
	eutra-CapabilityInfo-r12		OCTET STRING (CONTAINING UECapabilityInformation)	OPTIONAL,
	scg-ConfigRestrictInfo-r12		SCG-ConfigRestrictInfo-r12			OPTIONAL,
	mbmsInterestIndication-r12		OCTET STRING (CONTAINING
										MBMSInterestIndication-r11)		OPTIONAL,
	measResultServCellListSCG-r12	MeasResultServCellListSCG-r12		OPTIONAL,
	drb-ToAddModListSCG-r12			DRB-InfoListSCG-r12					OPTIONAL,
	drb-ToReleaseListSCG-r12		DRB-ToReleaseList					OPTIONAL,
	sCellToAddModListSCG-r12		SCellToAddModListSCG-r12			OPTIONAL,
	sCellToReleaseListSCG-r12		SCellToReleaseList-r10				OPTIONAL,
	p-Max-r12							P-Max								OPTIONAL,
	nonCriticalExtension			SCG-ConfigInfo-v13x0-IEs			OPTIONAL
}

SCG-ConfigInfo-v13x0-IEs ::=		SEQUENCE {
	measResultSSTD-r13				MeasResultSSTD-r13					OPTIONAL,	sCellToAddModListMCG-Ext-r13		SCellToAddModListExt-r13			OPTIONAL,
	measResultServCellListSCG-Ext-r13	MeasResultServCellListSCG-Ext-r13	OPTIONAL,
	sCellToAddModListSCG-Ext-r13		SCellToAddModListSCG-Ext-r13			OPTIONAL,
	sCellToReleaseListSCG-Ext-r13	SCellToReleaseListExt-r13			OPTIONAL,
	nonCriticalExtension			SEQUENCE {}							OPTIONAL
}

DRB-InfoListSCG-r12 ::=				SEQUENCE (SIZE (1..maxDRB)) OF DRB-InfoSCG-r12

DRB-InfoSCG-r12 ::=				SEQUENCE {
	eps-BearerIdentity-r12			INTEGER (0..15)				OPTIONAL,	-- Cond DRB-Setup
	drb-Identity-r12				DRB-Identity,
	drb-Type-r12					ENUMERATED {split, scg}		OPTIONAL,	-- Cond DRB-Setup
	...
}

SCellToAddModListSCG-r12 ::=	SEQUENCE (SIZE (1..maxSCell-r10)) OF Cell-ToAddMod-r12

SCellToAddModListSCG-Ext-r13 ::=	SEQUENCE (SIZE (maxSCell-Plus1..maxSCell-r13)) OF Cell-ToAddMod-r12

Cell-ToAddMod-r12 ::=				SEQUENCE {
	sCellIndex-r12						SCellIndex-r10,
	cellIdentification-r12				SEQUENCE {
		physCellId-r12						PhysCellId,
		dl-CarrierFreq-r12					ARFCN-ValueEUTRA-r9
	}																OPTIONAL,	-- Cond SCellAdd
	measResultCellToAdd-r12				SEQUENCE {
		rsrpResult-r12						RSRP-Range,
		rsrqResult-r12						RSRQ-Range
	}																OPTIONAL,	-- Cond SCellAdd2
	...,
	[[		sCellIndex-r13					SCellIndex-r13				OPTIONAL,
		measResultCellToAdd-v13xy			SEQUENCE {
			rs-sinrResult-r13					RS-SINR-Range-r13
		}															OPTIONAL	-- Cond SCellAdd2
	]]
}

MeasResultServCellListSCG-r12 ::=	SEQUENCE (SIZE (1..maxServCell-r10)) OF MeasResultServCellSCG-r12

MeasResultServCellListSCG-Ext-r13 ::=	SEQUENCE (SIZE (maxServCell-Plus1..maxServCell-r13)) OF MeasResultServCellSCG-r12

MeasResultServCellSCG-r12 ::=			SEQUENCE {
	servCellId-r12						ServCellIndex-r10,
	measResultSCell-r12					SEQUENCE {
		rsrpResultSCell-r12					RSRP-Range,
		rsrqResultSCell-r12					RSRQ-Range
	},
	...,
	[[		servCellId-r13						ServCellIndexFull-r13		OPTIONAL,
		measResultSCell-v13xy				SEQUENCE {
			rs-sinrResultSCell-r13				RS-SINR-Range-r13
		}															OPTIONAL
	]]
}

SCG-ConfigRestrictInfo-r12 ::=		SEQUENCE {
	maxSCH-TB-BitsDL-r12				INTEGER (1..100),
	maxSCH-TB-BitsUL-r12				INTEGER (1..100)
}

-- ASN1STOP

SCG-ConfigInfo field descriptions
drb-ToAddModListSCG
Includes DRBs the SeNB is requested to establish or modify (DRB type change).
drb-ToReleaseListSCG
Includes DRBs the SeNB is requested to release.
maxSCH-TB-BitsXL
Indicates the maximum DL-SCH/UL-SCH TB bits that may be scheduled in a TTI. Specified as a percentage of the value defined for the applicable UE category.
measGapConfig
Includes the current measurement gap configuration.
measResultSSTD
Includes measurement results of UE SSTD between the PCell and the PSCell.
measResultServCellListSCG
Includes measurement results of SCG (serving) cells.
radioResourceConfigDedMCG
Includes the current dedicated MCG radio resource configuration.
sCellIndex
If sCellIndex-r13 is present, sCellIndex-r12 shall be ignored.
sCellToAddModListMCG
Includes the current MCG SCell configuration.
sCellToAddModListSCG
Includes SCG cells the SeNB is requested to establish. Measurement results may be provided for these cells.
sCellToReleaseListSCG
Includes SCG cells the SeNB is requested to release.
scg-RadioConfig
Includes the current dedicated SCG configuration.
scg-ConfigRestrictInfo
Includes fields for which MeNB explictly indicates the restriction to be observed by SeNB.
servCellId
If servCellId-r13 is present, servCellId-r12 shall be ignored.
p-Max
Cell specific value i.e. as broadcast by PCell.

Conditional presence
Explanation
DRB-Setup
The field is mandatory present in case DRB establishment is requested; otherwise the field is not present.
SCellAdd
The field is mandatory present in case SCG cell establishment is requested; otherwise the field is not present.
SCellAdd2
The field is optional present in case SCG cell establishment is requested; otherwise the field is not present.

-	UERadioAccessCapabilityInformation
This message is used to transfer UE radio access capability information, covering both upload to and download from the EPC.
Direction: eNB to/ from EPC
UERadioAccessCapabilityInformation message
-- ASN1START

UERadioAccessCapabilityInformation ::= SEQUENCE {
	criticalExtensions					CHOICE {
		c1									CHOICE{
			ueRadioAccessCapabilityInformation-r8
												UERadioAccessCapabilityInformation-r8-IEs,
			spare7 NULL,
			spare6 NULL, spare5 NULL, spare4 NULL,
			spare3 NULL, spare2 NULL, spare1 NULL
		},
		criticalExtensionsFuture			SEQUENCE {}
	}
}

UERadioAccessCapabilityInformation-r8-IEs ::= SEQUENCE {
	ue-RadioAccessCapabilityInfo		OCTET STRING (CONTAINING UECapabilityInformation),
	nonCriticalExtension				SEQUENCE {}							OPTIONAL
}

-- ASN1STOP

UERadioAccessCapabilityInformation field descriptions
ue-RadioAccessCapabilityInfo
Including E-UTRA, GERAN, and CDMA2000-1xRTT Bandclass radio access capabilities (separated). UTRA radio access capabilities are not included.

-	UERadioPagingInformation
This message is used to transfer radio paging information, covering both upload to and download from the EPC.
Direction: eNB to/ from EPC
UERadioPagingInformation message
-- ASN1START

UERadioPagingInformation ::= SEQUENCE {
	criticalExtensions					CHOICE {
		c1									CHOICE{
			ueRadioPagingInformation-r12			UERadioPagingInformation-r12-IEs,
			spare7 NULL,
			spare6 NULL, spare5 NULL, spare4 NULL,
			spare3 NULL, spare2 NULL, spare1 NULL
		},
		criticalExtensionsFuture			SEQUENCE {}
	}
}

UERadioPagingInformation-r12-IEs ::= SEQUENCE {
	ue-RadioPagingInfo-r12				OCTET STRING (CONTAINING UE-RadioPagingInfo-r12),
	nonCriticalExtension				UERadioPagingInformation-v13xy-IEs			OPTIONAL
}

UERadioPagingInformation-v13xy-IEs ::= SEQUENCE {
	supportedBandListEUTRAForPaging-r13		SEQUENCE (SIZE (1..maxBands)) OF FreqBandIndicator-r11 OPTIONAL,
	nonCriticalExtension					SEQUENCE {}								OPTIONAL

}

-- ASN1STOP

UERadioPagingInformation field descriptions
ue-RadioPagingInfo 
The field is used to transfer radio paging information required for a category 0 UE. The eNB generates the ue-RadioPagingInfo and the contained ue-Category-v1250 is absent when the UE is not a category 0 UE.
supportedBandListEUTRAForPaging 
Indicates the UE supported frequency bands which is derived by the eNB from UE-EUTRA-Capability.

10.3	Inter-node RRC information element definitions
-	AS-Config
The AS-Config IE contains information about RRC configuration information in the source eNB which can be utilized by target eNB to determine the need to change the RRC configuration during the handover preparation phase. The information can also be used after the handover is successfully performed or during the RRC connection re-establishment.
AS-Config information element
-- ASN1START

AS-Config ::=				SEQUENCE {
	sourceMeasConfig					MeasConfig,
	sourceRadioResourceConfig			RadioResourceConfigDedicated,
	sourceSecurityAlgorithmConfig		SecurityAlgorithmConfig,
	sourceUE-Identity					C-RNTI,
	sourceMasterInformationBlock		MasterInformationBlock,
	sourceSystemInformationBlockType1	SystemInformationBlockType1(WITH COMPONENTS
											{..., nonCriticalExtension ABSENT}),
	sourceSystemInformationBlockType2	SystemInformationBlockType2,
	antennaInfoCommon					AntennaInfoCommon,
	sourceDl-CarrierFreq				ARFCN-ValueEUTRA,
	...,
	[[	sourceSystemInformationBlockType1Ext	OCTET STRING (CONTAINING
												SystemInformationBlockType1-v890-IEs)	OPTIONAL,
		sourceOtherConfig-r9				OtherConfig-r9
	-- sourceOtherConfig-r9 should have been optional. A target eNB compliant with this transfer
	-- syntax should support receiving an AS-Config not including this extension addition group
	-- e.g. from a legacy source eNB
	]],
	[[	sourceSCellConfigList-r10			SCellToAddModList-r10			OPTIONAL
	]],
	[[	sourceConfigSCG-r12					SCG-Config-r12		OPTIONAL
	]]
}

AS-Config-v9e0 ::=				SEQUENCE {
	sourceDl-CarrierFreq-v9e0		ARFCN-ValueEUTRA-v9e0
}

AS-Config-v10j0 ::=				SEQUENCE {
	antennaInfoDedicatedPCell-v10i0		AntennaInfoDedicated-v10i0			OPTIONAL
}

AS-Config-v1250 ::=				SEQUENCE {
	sourceWlan-OffloadConfig-r12		WLAN-OffloadConfig-r12				OPTIONAL,
	sourceSL-CommConfig-r12				SL-CommConfig-r12					OPTIONAL,
	sourceSL-DiscConfig-r12				SL-DiscConfig-r12					OPTIONAL
}

-- ASN1STOP
NOTE:	The AS-Config re-uses information elements primarily created to cover the radio interface signalling requirements. Consequently, the information elements may include some parameters that are not relevant for the target eNB e.g. the SFN as included in the MasterInformationBlock.

AS-Config field descriptions
antennaInfoCommon
This field provides information about the number of antenna ports in the source PCell.
sourceDL-CarrierFreq
Provides the parameter Downlink EARFCN in the source PCell, see TS 36.101 [42]. If the source eNB provides AS-Config-v9e0, it sets sourceDl-CarrierFreq (i.e. without suffix) to maxEARFCN.
sourceOtherConfig
Provides other configuration in the source PCell.
sourceMasterInformationBlock
MasterInformationBlock transmitted in the source PCell.
sourceMeasConfig
Measurement configuration in the source cell. The measurement configuration for all measurements existing in the source eNB when handover is triggered shall be included. See 10.5.
sourceSL-CommConfig
This field covers the sidelink communication configuration.
sourceSL-DiscConfig
This field covers the sidelink discovery configuration.
sourceRadioResourceConfig
Radio configuration in the source PCell. The radio resource configuration for all radio bearers existing in the source PCell when handover is triggered shall be included. See 10.5.
sourceSCellConfigList
Radio resource configuration (common and dedicated) of the SCells configured in the source eNB.
sourceSecurityAlgorithmConfig
This field provides the AS integrity protection (SRBs) and AS ciphering (SRBs and DRBs) algorithm configuration used in the source PCell.
sourceSystemInformationBlockType1
SystemInformationBlockType1 transmitted in the source PCell.
sourceSystemInformationBlockType2
SystemInformationBlockType2 transmitted in the source PCell.

-	AS-Context
The IE AS-Context is used to transfer local E-UTRAN context required by the target eNB.

AS-Context information element
-- ASN1START

AS-Context ::=							SEQUENCE {
	reestablishmentInfo						ReestablishmentInfo			OPTIONAL	-- Cond HO
}

AS-Context-v1130 ::=					SEQUENCE {
	idc-Indication-r11						OCTET STRING (CONTAINING
											InDeviceCoexIndication-r11)	OPTIONAL,	-- Cond HO2
	mbmsInterestIndication-r11				OCTET STRING (CONTAINING
											MBMSInterestIndication-r11)	OPTIONAL,	-- Cond HO2
	powerPrefIndication-r11					OCTET STRING (CONTAINING
											UEAssistanceInformation-r11)	OPTIONAL,	-- Cond HO2
	...,
	[[	sidelinkUEInformation-r12				OCTET STRING (CONTAINING
												SidelinkUEInformation-r12)	OPTIONAL	-- Cond HO2
	]]
}

-- ASN1STOP

AS-Context field descriptions
idc-Indication
Including information used for handling the IDC problems.
reestablishmentInfo
Including information needed for the RRC connection re-establishment.

Conditional presence
Explanation
HO
The field is mandatory present in case of handover within E-UTRA; otherwise the field is not present.
HO2
The field is optional present in case of handover within E-UTRA; otherwise the field is not present.

-	ReestablishmentInfo
The ReestablishmentInfo IE contains information needed for the RRC connection re-establishment.
ReestablishmentInfo information element
-- ASN1START

ReestablishmentInfo ::=				SEQUENCE {
	sourcePhysCellId					PhysCellId,
	targetCellShortMAC-I				ShortMAC-I,
	additionalReestabInfoList			AdditionalReestabInfoList				OPTIONAL,
	...
}

AdditionalReestabInfoList ::=		SEQUENCE ( SIZE (1..maxReestabInfo) ) OF AdditionalReestabInfo

AdditionalReestabInfo ::=	SEQUENCE{
	cellIdentity						CellIdentity,
	key-eNodeB-Star					Key-eNodeB-Star,
	shortMAC-I							ShortMAC-I
}

Key-eNodeB-Star ::=					BIT STRING (SIZE (256))

-- ASN1STOP

ReestablishmentInfo field descriptions
additionalReestabInfoList
Contains a list of shortMAC-I and KeNB* for cells under control of the target eNB, required for potential re-establishment by the UE in these cells to succeed.
Key-eNodeB-Star
Parameter KeNB*: See TS 33.401 [32, 7.2.8.4]. If the cell identified by cellIdentity belongs to multiple frequency bands, the source eNB selects the DL-EARFCN for the KeNB* calculation using the same logic as UE uses when selecting the DL-EARFCN in IDLE as defined in section 6.2.2. This parameter is only used for X2 handover, and for S1 handover, it shall be ignored by target eNB.
sourcePhyCellId
The physical cell identity of the source PCell, used to determine the UE context in the target eNB at re-establishment.
targetCellShortMAC-I
The ShortMAC-I for the handover target PCell, in order for potential re-establishment to succeed.

-	RRM-Config
The RRM-Config IE contains information about UE specific RRM information before the handover which can be utilized by target eNB.
RRM-Config information element
-- ASN1START

RRM-Config ::=				SEQUENCE {
	ue-InactiveTime				ENUMERATED {
									s1, s2, s3, s5, s7, s10, s15, s20,
									s25, s30, s40, s50, min1, min1s20c, min1s40,
									min2, min2s30, min3, min3s30, min4, min5, min6,
									min7, min8, min9, min10, min12, min14, min17, min20,
									min24, min28, min33, min38, min44, min50, hr1,
									hr1min30, hr2, hr2min30, hr3, hr3min30, hr4, hr5, hr6,
									hr8, hr10, hr13, hr16, hr20, day1, day1hr12, day2,
									day2hr12, day3, day4, day5, day7, day10, day14, day19,
									day24, day30, dayMoreThan30}		OPTIONAL,
	...,
	[[	candidateCellInfoList-r10	CandidateCellInfoList-r10		OPTIONAL
	]]
}

CandidateCellInfoList-r10 ::=	SEQUENCE (SIZE (1..maxFreq)) OF CandidateCellInfo-r10

CandidateCellInfo-r10 ::=		SEQUENCE {
	-- cellIdentification
	physCellId-r10					PhysCellId,
	dl-CarrierFreq-r10				ARFCN-ValueEUTRA,
	-- available measurement results
	rsrpResult-r10					RSRP-Range			OPTIONAL,
	rsrqResult-r10					RSRQ-Range			OPTIONAL,
	...,
	[[	dl-CarrierFreq-v1090			ARFCN-ValueEUTRA-v9e0		OPTIONAL
	]],
	[[	rsrqResult-v1250				RSRQ-Range-v1250			OPTIONAL
	]],
	[[	rs-sinrResult-v13xy				RS-SINR-Range-r13			OPTIONAL
	]]
}

-- ASN1STOP

RRM-Config field descriptions
candidateCellInfoList
A list of the best cells on each frequency for which measurement information was available, in order of decreasing RSRP.
dl-CarrierFreq
The source includes dl-CarrierFreq-v1090 if and only if dl-CarrierFreq-r10 is set to maxEARFCN.
ue-InactiveTime
Duration while UE has not received or transmitted any user data. Thus the timer is still running in case e.g., UE measures the neighbour cells for the HO purpose. Value s1 corresponds to 1 second, s2 corresponds to 2 seconds and so on. Value min1 corresponds to 1 minute, value min1s20 corresponds to 1 minute and 20 seconds, value min1s40 corresponds to 1 minute and 40 seconds and so on. Value hr1 corresponds to 1 hour, hr1min30 corresponds to 1 hour and 30 minutes and so on.

10.4	Inter-node RRC multiplicity and type constraint values
-	Multiplicity and type constraints definitions
-- ASN1START

maxReestabInfo				INTEGER ::= 32	-- Maximum number of KeNB* and shortMAC-I forwarded
											-- at handover for re-establishment preparation

-- ASN1STOP

-	End of EUTRA-InterNodeDefinitions
-- ASN1START

END
